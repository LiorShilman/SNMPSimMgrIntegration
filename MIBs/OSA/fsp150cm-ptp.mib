F3-PTP-MIB DEFINITIONS ::= BEGIN

IMPORTS
    MODULE-COMPLIANCE, OBJECT-GROUP, NOTIFICATION-GROUP
             FROM SNMPv2-CONF
    MODULE-IDENTITY, OBJECT-TYPE, NOTIFICATION-TYPE,
    IpAddress, Integer32, Unsigned32, Counter64, TimeTicks
             FROM SNMPv2-SMI
    DisplayString, TruthValue, RowStatus, StorageType, VariablePointer,
    MacAddress, DateAndTime, TEXTUAL-CONVENTION
             FROM SNMPv2-TC
    neIndex, shelfIndex, slotIndex
             FROM  CM-ENTITY-MIB
    cmEthernetAccPortIndex, cmEthernetNetPortIndex,
    cmEthernetAccPortEntry, cmEthernetNetPortEntry,
    cmEthernetTrafficPortIndex, cmEthernetTrafficPortEntry
             FROM  CM-FACILITY-MIB
    IpVersion, CmPmIntervalType, CmPmBinAction, F3DisplayString,
    AdminState, OperationalState, SecondaryState, PerfCounter64,
    IpPriorityMapMode, FlowSecState
             FROM  CM-COMMON-MIB
    fsp150cm
             FROM  ADVA-MIB
    AdminState, OperationalState, SecondaryState, 
          PerfCounter64, IpPriorityMapMode
             FROM  CM-COMMON-MIB
    SSMQualityLevel, HoldoverAccuracy, TimeSource
             FROM F3-SYNC-MIB
    Ipv6Address
             FROM  IPV6-TC
    CmGenPgSwitchoverReason, CmProtGropEntPrio
             FROM  CM-REDUNDANCY-MIB;

f3PtpMIB MODULE-IDENTITY
    LAST-UPDATED    "202211280000Z"
    ORGANIZATION    "ADVA Optical Networking SE"
    CONTACT-INFO
        "Web URL: http://adva.com/
        E-mail:  support@adva.com
        Postal:  ADVA Optical Networking SE
             Campus Martinsried
             Fraunhoferstrasse 9a
             82152 Martinsried/Munich
             Germany
        Phone: +49 089 89 06 65 0
        Fax:  +49 089 89 06 65 199 "
    DESCRIPTION
            "This module defines the 1588 PTP MIB definitions used by 
             the F3 (FSP150CM/CC) product lines.  
             Copyright (C) ADVA."
    REVISION        "202210180000Z"
    DESCRIPTION
         "
	 Notes from release 202211280000Z,
           (1) Added to F3PtpPTPPortEntry:
               f3PtpPTPPortIfName
	       	 	 
	  Notes from release 202210180000Z,
           (1) Added to F3PtpPTPClockEntry:
               f3PtpSynchronizationNotAssured

          Notes from release 202106040000Z,
           (1) Added bew literals to F3PtpPTPClockEntry:
                 f3PtpPTPClockCurrentOffsetFromMasterScaled,
                 f3PtpPTPClockRecentMeanPathDelayScaled,
                 f3PtpPTPClockRecentSyncPDVScaled

        Notes from release 202209100000Z
            (1) Added new column to F3PtpL3PTPPortEntry:
                f3PtpL3PTPPortMaxLeaseDuration,
                f3PtpL3PTPPortMaxSlavesSupported,
                f3PtpL3PTPPortMaxAnnounceMessageRate,
                f3PtpL3PTPPortMaxSyncMessageRate,
                f3PtpL3PTPPortMaxDelayRespMessageRate,
                f3PtpL3PTPPortMasterOnly
            (2) Added new table:
                f3PtpL3PTPPortStatsV2Table,
                f3PtpL3PTPPortHistoryV2Table,
                f3PtpL3DynamicRemoteSlaveTable,
                f3PtpL3RemoteSlaveStatsTable,
                f3PtpL3RemoteSlaveHistoryTable,
                f3PtpL3RemoteSlaveThresholdTable
            (3) Added new notification:
                f3PtpL3RemoteSlaveCrossingAlert,
                f3PtpL3DynamicRemoteSlaveStatusChangeTrap
		
       Notes from release 202206080000Z,
       (1)  Added to F3PtpL3PTPPortEntry:
              new attributes: 
              f3PtpL3PTPPortLastRcvdAnnounceMsg,
              f3PtpL3PTPPortLastRcvdSyncMsg,
              f3PtpL3PTPPortLastRcvdDelayReqMsg,
              f3PtpL3PTPPortLastRcvdDelayRspMsg 
               
       Notes from release 202205200000Z,
        (1)  Added to F3PtpL3PTPPortEntry:
                new attribute
                  f3PtpL3PTPPortVirtualPortCtrl

       Notes from release 202205050000Z,
        (1)  Added to F3PtpPTPPortEntry:
                new attributes 
                  f3PtpPTPPortScaledLogVariance
                  f3PtpPTPPortClockAccuracy
                  f3PtpPTPPortGMIdentity
                  f3PtpPTPPortStepsRemoved

        (2)  Added to F3PtpL3PTPPortEntry:
                new attributes 
                  f3PtpL3PTPPortScaledLogVariance
                  f3PtpL3PTPPortClockAccuracy
                  f3PtpL3PTPPortGMIdentity
                  f3PtpL3PTPPortStepsRemoved

       Notes from release 202204120000Z,
        (1)  Added to F3PtpPTPPortStatsEntry:
                new attributes 
                  f3PtpPTPPortStatsAvgLinkDelay 
                  f3PtpPTPPortStatsMinLinkDelay 
                  f3PtpPTPPortStatsMaxLinkDelay 

        (2)  Added to F3PtpPTPPortHistoryEntry:
                new attributes 
                  f3PtpPTPPortHistoryAvgLinkDelay 
                  f3PtpPTPPortHistoryMinLinkDelay 
                  f3PtpPTPPortHistoryMaxLinkDelay 


         Notes from release 202204030000Z,
           (1)  Added to F3PtpMCIEntry:
                  new attribute f3PtpMCIForcePRTCClockQuality
            
           (2)  Added to F3PtpPTPPortEntry
                  new attribute f3PtpPTPPortForcePRTCClockQuality
     
         Notes from release 202203100000Z,
           (1) Added to f3PtpL3PTPPortEntry:
               f3PtpL3PTPPortDelayReqDestIpAddrType
               
          Notes from release 202110280000Z,
           (1) Added new literal to PTPClockProfile:
               gptp-802-1as-2011(8)
                     
          Notes from release 202106040000Z,
           (1) Added new TEXTUAL-CONVENTION:
                 SlavesPercentage
                 with percent-75, percent-80, percent-90. percent-95, not-used
           (2) Added to F3PtpMCIEntry: 
                 f3PtpMCISlavesWarningThreshold 

          Notes from release 202104270000Z,
           (1) Change enum ProfileApplicationMode:
                 add literal fts

          Notes from release 202011090000Z,
           (1) Added new literals to F3PtpPTPClockEntry
              f3PtpPTPClockApplicationMode:

          Notes from release 202009100000Z,
           (1) Added new literals to PTPClockProfile:
                ieee-1588-2008-l3(8),
                enterprise(9)
                     
          Notes from release 202002100000Z,
           (1) Added new tables:
                f3PtpL3PTPPortStatsTable,
                f3PtpL3PTPPortHistoryTable,
                f3PtpL3PTPPortThresholdTable
           (2) Added new notification:
                f3PtpL3PTPPortCrossingAlert

          Notes from release 202002100000Z,
           (1) Added new literal to PTPClockProfile:
                power-c37-238-2011(3)
                     
          Notes from release 201912310000Z,
           (1) Added to f3PtpL3PTPPortEntry: 
                f3PtpL3PTPPortIndex,
                f3PtpL3PTPPortAdminState,
                f3PtpL3PTPPortAlias,          
                f3PtpL3PTPPortOperationalState,  
                f3PtpL3PTPPortSecondaryState,
                f3PtpL3PTPPortPortIdentity,    
                f3PtpL3PTPPortLocalPriority,         
                f3PtpL3PTPPortPtpFlowPointEid,         
                f3PtpL3PTPPortSyncMessageRate,   
                f3PtpL3PTPPortDelayReqRespMsgRate,
                f3PtpL3PTPPortAnnounceMsgRate,
                f3PtpL3PTPPortAnnounceReceiptTimeout,                            
                f3PtpL3PTPPortSyncReceiptTimeout,                            
                f3PtpL3PTPPortDelayRespTimeout,  
                f3PtpL3PTPPortPortState,
                f3PtpL3PTPPortBmcaDecisionCode, 
                f3PtpL3PTPPortPeerClockClass, 
                f3PtpL3PTPPortMinimumExpectedClockClass,
                f3PtpL3PTPPortIpProtocol,
                f3PtpL3PTPPortIfName,
                f3PtpL3PTPPortIpPriorityMapMode,
                f3PtpL3PTPPortIpPriority,
                f3PtpL3PTPPortIpV4Address,
                f3PtpL3PTPPortIpV4SubnetMask,
                f3PtpL3PTPPortIpV6Address,             
                f3PtpL3PTPPortIpV6AddrPrefixLength,
                f3PtpL3PTPPortDefaultGatewayControl,
                f3PtpL3PTPPortGateway,
                f3PtpL3PTPPortIpV6Gateway,
                f3PtpL3PTPPortUnicastMessageNegEnabled,
                f3PtpL3PTPPortTransmitDuration,
                f3PtpL3PTPPortRequestUnicastTimeout,
                f3PtpL3PTPPortRequestUnicastRestartTimer,
                f3PtpL3PTPPortMasterIpV4Address,
                f3PtpL3PTPPortMasterIpV6Address,
                f3PtpL3PTPPortDelayAsymmetryComp,
                f3PtpL3PTPPortAutoAsymmetryCompStatus,
                f3PtpL3PTPPortDelayAsymmetry,
                f3PtpL3PTPPortStorageType,
                f3PtpL3PTPPortRowStatus
        
          Notes from release 201912020000Z,
           (1) Added to f3PtpPTPPortEntry: 
                 f3PtpPTPPortTimeTraceable
                 f3PtpPTPPortFrequencyTraceable

          Notes from release 201911280000Z,
           (1) Added to f3PtpPTPPortEntry: 
                 f3PtpPTPPortDelayResponderType
                 
          Notes from release 201909090000Z,
           (1) Added to f3PtpPTPPortEntry: 
                 f3PtpPTPPortVirtualPortCtrl
                Notes from release 201907080000Z,
           (1) Added new TEXTUAL-CONVENTION to PTPClockProfile
                     - c37-238-2011, c37-238-2017 and iec-61850-9-3
           (2) Added f3PtpPTPClockGrandMasterID, f3PtpPTPClockTimeInaccuracy, f3PtpPTPClockNetworkTimeInaccuracy
           (3) Added f3PtpMasterClockSmpteSystemFrameRateNumerator, f3PtpMasterClockSmpteSystemFrameRateDenominator, 
                     f3PtpMasterClockSmpteTimeAddressFlags
           (4) Added f3PtpSOOCAlgorithmPtpAware

          Notes from release 201906180000Z,
           (1) Deprecated f3PtpPTPPortClockClass in favor of
               f3PtpPTPPortPeerClockClass

          Notes from release 201903140000Z,
           (1) Added new table:
                 f3PtpTrafficPortFlowPointExtTable to augment
                   f3PtpTrafficPortFlowPointTable with BufferSize

          Notes from release 201901310000Z,
           (1) Added to F3PtpSOOCEntry: 
                 f3PtpSOOCDefaultGatewayControl
                 f3PtpSOOCGateway              
                 f3PtpSOOCIpV6Gateway          

           (2) Added to F3PtpMCIEntry: 
                 f3PtpMCIDefaultGatewayControl 
                 f3PtpMCIGateway               
                 f3PtpMCIIpV6Gateway           

          Notes from release 201901240000Z,
           (1) Added table indices: 
                f3PtpMCIProtGroupIndex in f3PtpMCIProtMemberEntry
                
          Notes from release 201807300000Z,
           (1) New tables:
                 f3PtpMCIProtGroupTable,
                 f3PtpMCIProtMemberTable  
          Notes from release 201901070000Z
           (1) Added TEXTUAL-CONVENTION:: SlaveMode
           (2) Added f3PtpSOOCMasterMessageMode
           (3) Added f3PtpMasterClockServiceAvailableTime, 
                     f3PtpMasterClockServiceUnavailableTime, and 
                     f3PtpMasterClockServiceAvailablePercentage
           (4) Added f3PtpPTPClockServiceAvailableTime,
                     f3PtpPTPClockServiceUnavailableTime,
                     f3PtpPTPClockServiceAvailablePercentage
           (5) Added f3PtpPTPPortDelayAsymmetryComp,
                     f3PtpPTPPortAutoAsymmetryCompStatus, and
                     f3PtpPTPPortDelayAsymmetry

          Notes from release 201602170000Z
             a) add f3PtpBCPhysicalEntityIndex to f3PtpBCTable and adjust the index
          Notes from release 201601200000Z
             a) remove f3PtpPTPPortPTPPortType that is not supported and not in other products
          Notes from release 201512180000Z
             a) add f3PtpDynamicRemoteSlavePortIdentity and f3PtpDynamicRemoteSlavePeerMacAddress
             b) remove f3PtpMediationL2DynamicRemoteSlaveTable

          Notes from release 201512090000Z
           (1) add holdoverOutOfSpec, holdoverInSpec to ClockRecoveryState and PhaseRecoveryState
           (2) add f3PtpPTPClockClockClass to F3PtpPTPClockEntry
           (3) add PTPClockStats tables for PM on PTPClock

          Notes from release 201511160000Z
           (1) add f3PtpMCIPtpRemoteSlaveAgingTimeout to f3PtpMCITable

          Notes from release 201510290000Z
             (1) f3PtpMediationL2DynamicRemoteSlaveTable to support mediation version

          Notes from release 201510280000Z
             (1) added a new table (uncommented) f3PtpL2DynamicRemoteSlaveTable

          Notes from release 201510200000Z
             (1) removed  f3PtpAccPortFlowPointEIRLo, f3PtpAccPortFlowPointEIRHi, f3PtpPTPPortMaxExpectedL2Slaves

             (2) added f3PtpMCIPtpTransport, f3PtpMCIPtpTransportMode, f3PtpBCMediationControl


          Notes from release 201309240000Z,
           (1) Added the following object
                f3PtpDynamicRemoteSlaveRowStatus
                    
          Notes from release 201304240000Z,
           (1) New tables: f3PtpMasterClockTable
                    
          Notes from release 201301170000Z,
           (1) New tables: f3PtpBCTable, f3PtpMCITable, f3PtpMasterVirtualPortTable,
                           f3PtpRemoteSlaveTable,
                           f3PtpMCIStatsTable, f3PtpMCIHistoryTable, 
                           f3PtpMCIThresholdTable,
                           f3PtpRemoteSlaveStatsTable, f3PtpRemoteSlaveHistoryTable
                           f3PtpRemoteSlaveThresholdTable
           (2) New notifications: f3PtpMCICrossingAlert, f3PtpRemoteSlaveCrossingAlert  

          Notes from release 201207190000Z,
           (1) New tables: f3PtpEthernetAccPortExtTable, f3PtpEthernetNetPortExtTable  

          Notes from release 201206130000Z
            (i)Added the following objects
                f3PtpTSClockSyncEEnabled, f3PtpTSClockQLModeEnabled,
                f3PtpTSClockExpectedQL, f3PtpTSClockAssumedQL,
                f3PtpTSClockReceivedQL, 

          Notes from release 201205180000Z
            (i)INDEX objects are made not-accessible

          Notes from release 201105060000Z
            (i)f3PtpAccPortFlowPointService and f3PtpNetPortFlowPointService are
                    read-create instead of read-only
           (ii)Threshold Crossing Notifications are now defined
                f3PtpAccPortFlowPointThresholdCrossingAlert,
                f3PtpNetPortFlowPointThresholdCrossingAlert,
                f3PtpSOOCCrossingAlert 

          Notes from release 201104040000Z
          Initial version of the MIB, now with Performance Objects." 
    ::= {fsp150cm 18}    

--
-- OID definitions
--
f3PtpConfigObjects             OBJECT IDENTIFIER ::= {f3PtpMIB 1}
f3PtpPerformanceObjects        OBJECT IDENTIFIER ::= {f3PtpMIB 2}
f3PtpPerformanceNotifications  OBJECT IDENTIFIER ::= {f3PtpMIB 3}
f3PtpConformance               OBJECT IDENTIFIER ::= {f3PtpMIB 4}
f3PtpStatusChangeNotifications OBJECT IDENTIFIER ::= {f3PtpMIB 5}

--
-- Textual Conventions 
--
SlaveMode ::= TEXTUAL-CONVENTION
    STATUS         current
    DESCRIPTION
        "Describes the PTP slave mode on OSA540X."
    SYNTAX      INTEGER {
                    not-applicable(0),
                    unicast (1),
                    multicast (2),
                    hybrid (3)
                }

PtpFlowPointType ::= TEXTUAL-CONVENTION
    STATUS       current
    DESCRIPTION
        "Enumerations for PTP Flow Point Type.
             transparent - represents the 1588 Transparent clock type,
             oc-slave - represents a 1588 Ordinary Clock Slave clock type,
             monitoring - represents monitoring Flow Point,
             oc-master - represents a 1588 Ordinary Clock master clock type."
    SYNTAX       INTEGER {
                   transparent (1),
                   oc-slave (2),
                   monitoring(3),
                   oc-master(4),
                   eth-multicast(5),
                   l3(6)
                 }

PtpPortState ::= TEXTUAL-CONVENTION
    STATUS       current
    DESCRIPTION
          "Enumerations for PTP Port State."
    SYNTAX   INTEGER {
               initializing(1),
               faulty(2),
               disabled(3),
               listening(4),
               uncalibrated(5),
               slave(6),
               premaster(7),
               master(8),  
               passive(9),
               na(10) 
             }

MasterClockType ::= TEXTUAL-CONVENTION
    STATUS       current
    DESCRIPTION
          "Enumerations for Master Clock Type."
    SYNTAX   INTEGER {
               unknown(1),
               one-step(2),
               two-step(3)
             }

PTPPortType ::= TEXTUAL-CONVENTION
    STATUS       current
    DESCRIPTION
          "Enumerations for PTP Port Type."
    SYNTAX   INTEGER {
               master(1),
               slave(2)
             }

DelayMechanism ::= TEXTUAL-CONVENTION
    STATUS       current
    DESCRIPTION
          "Enumerations for Delay Mechanism."
    SYNTAX   INTEGER {
               end-to-end(1),
	       peer-to-peer(2)
             }

ClockIdentity ::= TEXTUAL-CONVENTION
    STATUS       current
    DESCRIPTION
          "1588 Clock Identity."
    SYNTAX       OCTET STRING (SIZE(8))

PortIdentity ::= TEXTUAL-CONVENTION
    STATUS       current
    DESCRIPTION
          "1588 Port Identity."
    SYNTAX       OCTET STRING (SIZE(10))


ClockRecoveryMode ::= TEXTUAL-CONVENTION
    STATUS       current
    DESCRIPTION
          "Enumerations for 1588 Clock Recovery Mode."
    SYNTAX   INTEGER {
               one-way(1),
               two-way(2)
             }

ClockRecoveryState ::= TEXTUAL-CONVENTION
    STATUS       current
    DESCRIPTION
          "Enumerations for 1588 Clock Recovery State."
    SYNTAX   INTEGER {
               not-applicable(0),
               start(1),
               normal(2),
               freerun(3),
               holdover(4),
               acquisition(5),
               transient(6),
               none(7),
               holdoverOutOfSpec(8),
               holdoverInSpec(9)
             }

AnnounceMsgRate ::= TEXTUAL-CONVENTION
    STATUS       current
    DESCRIPTION
          "Enumerations for 1588 Announce Message Rate."
    SYNTAX   INTEGER {
               not-applicable(0),
               pkt1per16secs(1),
               pkt1per8secs(2),
               pkt1per4secs(3),
               pkt1per2secs(4),
               pkt1per1sec(5),
               pkts2per1sec(6),
               pkts4per1sec(7),
               pkts8per1sec(8),
               none(9)
            }

SyncMsgRate ::= TEXTUAL-CONVENTION
    STATUS       current
    DESCRIPTION
          "Enumerations for 1588 Sync Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
             }

DelayRespMsgRate ::= TEXTUAL-CONVENTION
    STATUS       current
    DESCRIPTION
          "Enumerations for 1588 Delay Response Message Rate."
    SYNTAX   INTEGER {
               not-applicable(0),
               pkt1persec(1),
               pkts2persec(2),
               pkts4persec(3),
               pkts8persec(4),
               pkts16persec(5),
               pkts32persec(6),
               pkts64persec(7),
               pkts128persec(8),
               none(9),
               na(10),
               pkts0persec(11)
             }

DelayReqMsgRate ::= TEXTUAL-CONVENTION
    STATUS       current
    DESCRIPTION
          "Enumerations for 1588 Delay Request Message Rate."
    SYNTAX   INTEGER {
               not-applicable(0),
               pkt1persec(1),
               pkts2persec(2),
               pkts4persec(3),
               pkts8persec(4),
               pkts16persec(5),
               pkts32persec(6),
               pkts64persec(7),
               pkts128persec(8)
             }

FreqRecoveryTarget ::= TEXTUAL-CONVENTION
    STATUS       current
    DESCRIPTION
          "Enumerations for Frequency Recovery Target."
    SYNTAX   INTEGER {
               not-applicable(0),
               traffic-mask(1),
               sync-mask(2),
               traffic-sync-mask(3)
             }

ScaledNanoseconds ::= TEXTUAL-CONVENTION
    STATUS       current
    DESCRIPTION
          "Definition of scaled nanoseconds as specified by 1588v2.
           The most significant 48 bits represent nanoseconds and 
           the least signifcant 16-bits represent sub-nanoseconds.
           The currently supported granularity is nanoseconds and
           the least significant 16 bits will always be 0.
           The 48-bits representing nanoseconds supports the range
           of [-2^47..2^47-1].
           Negative values of nanonseconds are interpreted
           as two's complement."
    SYNTAX   Counter64

RemoteSlaveType ::= TEXTUAL-CONVENTION
    STATUS       current
    DESCRIPTION
          "Enumerations for Remote Slave Type."
    SYNTAX   INTEGER {
               dynamic(1),
               static(2)
             }

TimeScale ::= TEXTUAL-CONVENTION
    STATUS       current
    DESCRIPTION
          ""
    SYNTAX   INTEGER {
               ptp(1),
               arb(2)
             }

PhaseRecoveryState ::= TEXTUAL-CONVENTION
    STATUS       current
    DESCRIPTION
          "Enumerations for Phase Recovery State."
    SYNTAX   INTEGER {
               not-applicable(0),
               freerun(1),
               holdover(2),
               normal(3),
               start(4),
               acquisition(5),
               transient(6),
               none(7),
               holdoverOutOfSpec(8),
               holdoverInSpec(9)
             }

PTPProtectionState ::= TEXTUAL-CONVENTION
    STATUS       current
    DESCRIPTION
          "Enumerations for PTP Protection State."
    SYNTAX   INTEGER {
               active(1),
               standby(2)
             }

CompensationMode ::= TEXTUAL-CONVENTION
    STATUS       current
    DESCRIPTION
          "Enumerations for Compensation Mode."
    SYNTAX   INTEGER {
               disabled(1),
               automatic(2),
               manual(3)
             }

CompensationStatus ::= TEXTUAL-CONVENTION
    STATUS       current
    DESCRIPTION
          "Enumerations for Compensation Status."
    SYNTAX   INTEGER {
               operational(1),
               failed(2),
               not-available(3),
               manual(4),
               initializing(5)
             }

PTPClockProfile ::= TEXTUAL-CONVENTION
    STATUS       current
    DESCRIPTION
          "Enumerations for PTP Clock Profile."
    SYNTAX   INTEGER {
               g8275-1(1),
               ieee-1588-2008-annex-f(2),
               ieee-1588-2008(3),
               power-c37-238-2011(4),
               power-c37-238-2017(5),
               utility-iec-61850-9-3(6),
               g8275-2(7),
               gptp-802-1as-2011(8),
               ieee-1588-2008-l3(9),
               enterprise(10)
             }

PTPClockType ::= TEXTUAL-CONVENTION
    STATUS       current
    DESCRIPTION
          "Enumerations for PTP Clock Type."
    SYNTAX   INTEGER {
               master-only(1),
               slave-only(2),
               dynamic(3),
               boundaryclock(4),
               static-bc(5)
             }

PTPClockOperMode ::= TEXTUAL-CONVENTION
    STATUS       current
    DESCRIPTION
          "Enumerations for PTP Clock Oper Mode."
    SYNTAX   INTEGER {
               t-gm(1),
               t-tsc(2),
               idle(3),
               t-bc(4),
               gm(5)
             }

DestMacAddrType ::= TEXTUAL-CONVENTION
    STATUS       current
    DESCRIPTION
          "Enumerations for Dest Mac Addr Type."
    SYNTAX   INTEGER {
               forwardable(1),
               non-forwardable(2)
             }


AnnounceMessageRate ::= TEXTUAL-CONVENTION
    STATUS       current
    DESCRIPTION
          "Enumerations for g8275.1 Announce Message Rate."
    SYNTAX   INTEGER {
               not-applicable(0),
               pkt1per16secs(1),
               pkt1per8secs(2),
               pkt1per4secs(3),
               pkt1per2secs(4),
               pkt1per1sec(5),
               pkts2per1sec(6),
               pkts4per1sec(7),
               pkts8per1sec(8),
               none(9)        
            }

DelayReqMessageRate ::= TEXTUAL-CONVENTION
    STATUS       current
    DESCRIPTION
          "Enumerations for g8275.1 Delay Req Message Rate."
    SYNTAX   INTEGER {
               not-applicable(0),
               pkt1persec(1),
               pkts2persec(2),
               pkts4persec(3),
               pkts8persec(4),
               pkts16persec(5),
               pkts32persec(6),
               pkts64persec(7),
               pkts128persec(8),
               none(9),
               na(10)
            }

SyncMessageRate ::= TEXTUAL-CONVENTION
    STATUS       current
    DESCRIPTION
          "Enumerations for g8275.1 Sync Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
            }

BMCARole ::= TEXTUAL-CONVENTION
    STATUS       current
    DESCRIPTION
          "Enumerations for g8275.1 BMCA Role."
    SYNTAX   INTEGER {
               m1(1),  
               m2(2),   
               m3(3),   
               s1(4),   
               p1(5),    
               p2(6),   
               na(7)   
            }


ClockClassProfile ::= TEXTUAL-CONVENTION
    STATUS       current
    DESCRIPTION
          "Enumerations for Master Clock Interface the Clock Class Profile."
    SYNTAX   INTEGER {
               g82651(1),  
               ieee-1588-2008(2),
               ptp-enterprise(3),
               na(4),
               g82752(5),
               ptp-enterprise-and-ieee-1588-2008(6)

            }

PTPProfile ::= TEXTUAL-CONVENTION
    STATUS       current
    DESCRIPTION
          "Enumerations for Master Clock PTP Profile."
    SYNTAX   INTEGER {
               g82651(1),  
               ptp-enterprise(2),
               ieee-1588-2008(3),
               g82752(4),
               aes67-media(5),
               smpte-st-2059-2(6)
            }

PTPTransport ::= TEXTUAL-CONVENTION
    STATUS       current
    DESCRIPTION
          "Enumerations for Master Clock Interface PTP Transport Type."
    SYNTAX   INTEGER {
               ethernet(1),  
               udp-over-ipv4(2),  
               udp-over-ipv6(3)  
            }

PTPTransportMode ::= TEXTUAL-CONVENTION
    STATUS       current
    DESCRIPTION
          "Enumerations for Master Clock Interface PTP Transport mode."
    SYNTAX   INTEGER {
               unicast(1),  
               multicast(2)
            }


ToggleValue ::= TEXTUAL-CONVENTION
    STATUS         current
    DESCRIPTION    "Enumerations for functionality that can be enabled or disabled."
    SYNTAX INTEGER    {
        enabled(1),
        disabled(2),
        not-available(3)
        }

ProfileApplicationMode ::= TEXTUAL-CONVENTION
    STATUS       current
    DESCRIPTION
          "Enumerations for PTP Clock Application mode."
    SYNTAX   INTEGER {
               telecom-pts(1),  
               docsis(2),
               fts(3)
            }

SlavesPercentage ::= TEXTUAL-CONVENTION
    STATUS       current
    DESCRIPTION
          "Enumerations for various proportions of a set of Slaves."
    SYNTAX   INTEGER {
               percent-70(1),  
               percent-80(2),
               percent-90(3),
               percent-95(4),
               not-used(5)
            }

--
-- CONFIGURATION 
--
-- Transparent Clock Table 
--
f3PtpTCTable OBJECT-TYPE
    SYNTAX     SEQUENCE OF F3PtpTCEntry 
    MAX-ACCESS not-accessible
    STATUS     current
    DESCRIPTION
       "A list of entries corresponding to the PTP Transparent Clock entities."
    ::= { f3PtpConfigObjects 1 }

f3PtpTCEntry OBJECT-TYPE
    SYNTAX     F3PtpTCEntry
    MAX-ACCESS not-accessible
    STATUS     current
    DESCRIPTION
          "An entry containing information applicable to a particular
           Transparent Clock Entity."
    INDEX { neIndex, f3PtpTCIndex}
    ::= { f3PtpTCTable 1 }


F3PtpTCEntry ::= SEQUENCE {
    f3PtpTCIndex              Integer32,

    f3PtpTCAlias              DisplayString,

    f3PtpTCAdminState         AdminState,
    f3PtpTCOperationalState   OperationalState,
    f3PtpTCSecondaryState     SecondaryState,

    f3PtpTCServiceFlow        VariablePointer,
    f3PtpTCDelayMechanism     DelayMechanism,
    f3PtpTCSync               VariablePointer,
    f3PtpTCClockIdentity      ClockIdentity,

    f3PtpTCStorageType        StorageType,
    f3PtpTCRowStatus          RowStatus,
    f3PtpTCPtpProfile         PTPClockProfile
}

f3PtpTCIndex OBJECT-TYPE
    SYNTAX     Integer32
    MAX-ACCESS not-accessible 
    STATUS     current
    DESCRIPTION
         "Unique index value associated with the Transparent Clock Entity."
     ::= { f3PtpTCEntry 1 }

f3PtpTCAlias    OBJECT-TYPE
    SYNTAX      DisplayString (SIZE(0..256))
    MAX-ACCESS  read-create
    STATUS      current
    DESCRIPTION
         "This object allows SNMP management entities to provide an 
          alias to the Transparent Clock entity."
     ::= { f3PtpTCEntry 2 }

f3PtpTCAdminState OBJECT-TYPE
    SYNTAX      AdminState 
    MAX-ACCESS  read-write
    STATUS      current
    DESCRIPTION
          "This object represents the Administrative State of the Transparent Clock."
    ::= { f3PtpTCEntry 3 }

f3PtpTCOperationalState   OBJECT-TYPE
    SYNTAX      OperationalState 
    MAX-ACCESS  read-only
    STATUS      current
    DESCRIPTION
          "This object represents the Operational State of the Transparent Clock." 
    ::= { f3PtpTCEntry 4 }

f3PtpTCSecondaryState     OBJECT-TYPE
    SYNTAX      SecondaryState 
    MAX-ACCESS  read-only
    STATUS      current
    DESCRIPTION
           "This object represents the Secondary State of the Transparent Clock."
    ::= { f3PtpTCEntry 5 }

f3PtpTCServiceFlow OBJECT-TYPE
    SYNTAX      VariablePointer 
    MAX-ACCESS  read-create
    STATUS      current
    DESCRIPTION
            "This object represents the Service(Traffic) Flow associated
             with the Transparent Clock."
    ::= { f3PtpTCEntry 6 }

f3PtpTCDelayMechanism OBJECT-TYPE
    SYNTAX      DelayMechanism 
    MAX-ACCESS  read-create
    STATUS      current
    DESCRIPTION
            "This object  represents the Delay Mechanism of the Transparent 
             Clock."
    ::= { f3PtpTCEntry 7 }

f3PtpTCSync OBJECT-TYPE
    SYNTAX     VariablePointer 
    MAX-ACCESS read-create
    STATUS     current
    DESCRIPTION
         "This object provides the entry from the f3SyncTable, which is
          used as frequency clock for this Transparent Clock."
     ::= { f3PtpTCEntry 8 }

f3PtpTCClockIdentity OBJECT-TYPE
    SYNTAX     ClockIdentity 
    MAX-ACCESS read-create
    STATUS     current
    DESCRIPTION
         "This object specifies the Clock Identity of the PTP Transparent Clock." 
     ::= { f3PtpTCEntry 9 }

f3PtpTCStorageType OBJECT-TYPE
    SYNTAX     StorageType
    MAX-ACCESS read-create
    STATUS     current
    DESCRIPTION
            "The type of storage configured for this entry."
    ::= { f3PtpTCEntry 10 }

f3PtpTCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTCRowStatus supported are
            createAndGo(4) and destroy(6).  All mandatory attributes
            must be specified in a single SNMP SET request with
            f3PtpTCRowStatus value as createAndGo(4).
            Upon successful row creation, this object has a
            value of active(1).

            The f3PtpTCRowStatus object may be modified if
            the associated instance of this object is equal to active(1)."
    ::= { f3PtpTCEntry 11 }

f3PtpTCPtpProfile     OBJECT-TYPE
    SYNTAX      PTPClockProfile 
    MAX-ACCESS  read-create
    STATUS      current
    DESCRIPTION
           "This object represents whether Tc or T-Tc."
    ::= { f3PtpTCEntry 12 }

--
-- PTP Transparent Clock Virtual Port Table 
--
f3PtpTCVirtualPortTable OBJECT-TYPE
    SYNTAX     SEQUENCE OF F3PtpTCVirtualPortEntry 
    MAX-ACCESS not-accessible
    STATUS     current
    DESCRIPTION
         "A list of entries corresponding to the PTP Transparent 
          Clock Virtual Ports."
    ::= { f3PtpConfigObjects 2 }

f3PtpTCVirtualPortEntry OBJECT-TYPE
    SYNTAX     F3PtpTCVirtualPortEntry
    MAX-ACCESS not-accessible
    STATUS     current
    DESCRIPTION
          "An entry containing information applicable to a particular
           PTP TC Virtual Port Entity."
    INDEX { neIndex, f3PtpTCIndex,  f3PtpTCVirtualPortIndex }
    ::= { f3PtpTCVirtualPortTable 1 }

F3PtpTCVirtualPortEntry ::= SEQUENCE {
    f3PtpTCVirtualPortIndex              Integer32,

    f3PtpTCVirtualPortAlias              DisplayString,

    f3PtpTCVirtualPortAdminState         AdminState,
    f3PtpTCVirtualPortOperationalState   OperationalState,
    f3PtpTCVirtualPortSecondaryState     SecondaryState,

    f3PtpTCVirtualPortIdentity           PortIdentity,
    f3PtpTCVirtualPortFlowPoint          VariablePointer,
    f3PtpTCVirtualPortStorageType        StorageType,
    f3PtpTCVirtualPortRowStatus          RowStatus
}

f3PtpTCVirtualPortIndex OBJECT-TYPE
    SYNTAX     Integer32
    MAX-ACCESS not-accessible
    STATUS     current
    DESCRIPTION
         "Unique index value associated with the PTP Transparent Clock
          Virtual Port index."
     ::= { f3PtpTCVirtualPortEntry 1 }

f3PtpTCVirtualPortAlias    OBJECT-TYPE
    SYNTAX      DisplayString (SIZE(0..256))
    MAX-ACCESS  read-create
    STATUS      current
    DESCRIPTION
         "This object allows SNMP management entities to provide an 
          alias to the PTP TC Virtual Port entity."
     ::= { f3PtpTCVirtualPortEntry 2 }

f3PtpTCVirtualPortAdminState OBJECT-TYPE
    SYNTAX      AdminState 
    MAX-ACCESS  read-write
    STATUS      current
    DESCRIPTION
            "This object represents the Administrative State of the TC Virtual 
             Port."
    ::= { f3PtpTCVirtualPortEntry 3 }

f3PtpTCVirtualPortOperationalState   OBJECT-TYPE
    SYNTAX      OperationalState 
    MAX-ACCESS  read-only
    STATUS      current
    DESCRIPTION
            "This object represents the Operational State of the TC Virtual 
             Port."
    ::= { f3PtpTCVirtualPortEntry 4 }

f3PtpTCVirtualPortSecondaryState     OBJECT-TYPE
    SYNTAX      SecondaryState 
    MAX-ACCESS  read-only
    STATUS      current
    DESCRIPTION
           "This object represents the Secondary State of the TC Virtual Port." 
    ::= { f3PtpTCVirtualPortEntry 5 }

f3PtpTCVirtualPortIdentity OBJECT-TYPE
    SYNTAX     PortIdentity 
    MAX-ACCESS read-write
    STATUS     current
    DESCRIPTION
         "This object represents the PTP Port Identity of the TC Virtual Port." 
     ::= { f3PtpTCVirtualPortEntry 6 }

f3PtpTCVirtualPortFlowPoint OBJECT-TYPE
    SYNTAX     VariablePointer 
    MAX-ACCESS read-create
    STATUS     current
    DESCRIPTION
         "This object associates the PTP Flow Point with the 
          Transparent Clock."
     ::= { f3PtpTCVirtualPortEntry 7 }

f3PtpTCVirtualPortStorageType OBJECT-TYPE
    SYNTAX     StorageType
    MAX-ACCESS read-create
    STATUS     current
    DESCRIPTION
            "The type of storage configured for this entry."
    ::= { f3PtpTCVirtualPortEntry 8 }

f3PtpTCVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTCVirtualPortRowStatus supported are
            createAndGo(4) and destroy(6).  All mandatory attributes
            must be specified in a single SNMP SET request with
            f3PtpTCVirtualPortRowStatus value as createAndGo(4).
            Upon successful row creation, this object has a
            value of active(1).

            The f3PtpTCVirtualPortRowStatus object may be modified if
            the associated instance of this object is equal to active(1)."
    ::= { f3PtpTCVirtualPortEntry 9 }


--
-- Telecom Slave Table 
--
f3PtpTSTable OBJECT-TYPE
    SYNTAX     SEQUENCE OF F3PtpTSEntry 
    MAX-ACCESS not-accessible
    STATUS     current
    DESCRIPTION
       "A list of entries corresponding to the PTP Telecom Slave entities."
    ::= { f3PtpConfigObjects 3 }

f3PtpTSEntry OBJECT-TYPE
    SYNTAX     F3PtpTSEntry
    MAX-ACCESS not-accessible
    STATUS     current
    DESCRIPTION
          "An entry containing information applicable to a particular
           Telecom Slave Entity."
    INDEX { neIndex, f3PtpTSIndex}
    ::= { f3PtpTSTable 1 }

F3PtpTSEntry ::= SEQUENCE {
    f3PtpTSIndex                             Integer32,

    f3PtpTSAlias                             DisplayString,

    f3PtpTSAdminState                        AdminState,
    f3PtpTSOperationalState                  OperationalState,
    f3PtpTSSecondaryState                    SecondaryState,

    f3PtpTSClockIdentity                     ClockIdentity,
    f3PtpTSDomainNumber                      Integer32,
    f3PtpTSSync                              VariablePointer,
    f3PtpTSCurrentTOD                        DateAndTime,
    f3PtpTSSelectedPacketClock               VariablePointer,

    f3PtpTSClockRecoveryMode                 ClockRecoveryMode,
    f3PtpTSClockRecoveryState                ClockRecoveryState,

    f3PtpTSClockSyncEEnabled                 TruthValue,
    f3PtpTSClockQLModeEnabled                TruthValue,
    f3PtpTSClockExpectedQL                   SSMQualityLevel,
    f3PtpTSClockAssumedQL                    SSMQualityLevel,
    f3PtpTSClockReceivedQL                   SSMQualityLevel,

    f3PtpTSStorageType                       StorageType,
    f3PtpTSRowStatus                         RowStatus,

    f3PtpTSTimeTraceabilityStatus            TruthValue,
    f3PtpTSTimeSinceTimeTraceabilityChanged  Unsigned32,
    f3PtpTSFreqTraceabilityStatus            TruthValue,
    f3PtpTSTimeSinceFreqTraceabilityChanged  Unsigned32,
    f3PtpTSFreqRecoveryTarget                FreqRecoveryTarget,
    f3PtpTSCurrentCRScore                    Unsigned32,
    f3PtpTSTimeLastCRScore                   DateAndTime,
    f3PtpTSTargetPhaseRecoveryAccuracy       Unsigned32,
    f3PtpTSCurrentPRScore                    Unsigned32,
    f3PtpTSTimeLastPRScore                   DateAndTime,
    f3PtpTSClockClass                        Unsigned32,
    f3PtpTSClockAccuracy                     Unsigned32,
    f3PtpTSTimeSource                        TimeSource,
    f3PtpTSPhaseRecoveryState                PhaseRecoveryState, 
    f3PtpTSTimeHoldoverAccuracy              HoldoverAccuracy,
    f3PtpTSWtrTime                           Integer32
}

f3PtpTSIndex OBJECT-TYPE
    SYNTAX     Integer32
    MAX-ACCESS not-accessible 
    STATUS     current
    DESCRIPTION
         "Unique index value associated with the Telecom Slave Entity."
     ::= { f3PtpTSEntry 1 }

f3PtpTSAlias    OBJECT-TYPE
    SYNTAX      DisplayString (SIZE(0..256))
    MAX-ACCESS  read-create
    STATUS      current
    DESCRIPTION
         "This object allows SNMP management entities to provide an 
          alias to the Telecom Slave entity."
     ::= { f3PtpTSEntry 2 }

f3PtpTSAdminState OBJECT-TYPE
    SYNTAX      AdminState 
    MAX-ACCESS  read-write
    STATUS      current
    DESCRIPTION
          "This object represents the Administrative State of the Telecom Slave."
    ::= { f3PtpTSEntry 3 }

f3PtpTSOperationalState   OBJECT-TYPE
    SYNTAX      OperationalState 
    MAX-ACCESS  read-only
    STATUS      current
    DESCRIPTION
          "This object represents the Operational State of the Telecom Slave." 
    ::= { f3PtpTSEntry 4 }

f3PtpTSSecondaryState     OBJECT-TYPE
    SYNTAX      SecondaryState 
    MAX-ACCESS  read-only
    STATUS      current
    DESCRIPTION
           "This object represents the Secondary State of the Telecom Slave."
    ::= { f3PtpTSEntry 5 }

f3PtpTSClockIdentity OBJECT-TYPE
    SYNTAX     ClockIdentity 
    MAX-ACCESS read-create
    STATUS     current
    DESCRIPTION
         "This object specifies the Clock Identity of the PTP Telecom Slave." 
     ::= { f3PtpTSEntry 6 }

f3PtpTSDomainNumber OBJECT-TYPE
    SYNTAX     Integer32 
    MAX-ACCESS read-write
    STATUS     current
    DESCRIPTION
         "This object allows specification of the PTP domain number of the
          Telecom Slave." 
     ::= { f3PtpTSEntry 7 }

f3PtpTSSync OBJECT-TYPE
    SYNTAX     VariablePointer 
    MAX-ACCESS read-create
    STATUS     current
    DESCRIPTION
         "This object provides the entry from the f3SyncTable, which is
          used as frequency for this Telecom Slave."
     ::= { f3PtpTSEntry 8 }

f3PtpTSCurrentTOD OBJECT-TYPE
    SYNTAX     DateAndTime 
    MAX-ACCESS read-only
    STATUS     current
    DESCRIPTION
         "This object allows specification of the Telecom Slave Current
          Time of Day." 
     ::= { f3PtpTSEntry 9 }

f3PtpTSSelectedPacketClock OBJECT-TYPE
    SYNTAX     VariablePointer 
    MAX-ACCESS read-only
    STATUS     current
    DESCRIPTION
         "This object provides the Slave Only Ordinary Clock selected
          as the best source of Time Of Day."
     ::= { f3PtpTSEntry 10 }

f3PtpTSClockRecoveryMode    OBJECT-TYPE 
    SYNTAX     ClockRecoveryMode 
    MAX-ACCESS read-create
    STATUS     current
    DESCRIPTION
         "This object allows specification of whether the Clock Recovery Mode
          is one-way or two-way.  In one-way mode, only Sync messages are
          used for frequency recovery.  In two-way mode, both Sync and 
          Delay Request-Response messages are used for measuring the mean path delay." 
     ::= { f3PtpTSEntry 11 }

f3PtpTSClockRecoveryState    OBJECT-TYPE 
    SYNTAX     ClockRecoveryState 
    MAX-ACCESS read-only
    STATUS     current
    DESCRIPTION
         "This object provides the Telecom Slave's clock recovery state." 
     ::= { f3PtpTSEntry 12 }

--Synchronous Port params
f3PtpTSClockSyncEEnabled OBJECT-TYPE 
    SYNTAX     TruthValue
    MAX-ACCESS read-write
    STATUS     current
    DESCRIPTION
         "This object allows to specify whether the Telecom Slave 
          can be enabled/disabled for Synchronous Ethernet. 
          When enabled, on receive side 
            -telecom slave can extract the frequency 
             and pass the recovered clock to the system clock
            -QL is extracted (when QL is enabled) from the selected SOOC's clock class
            -telecom slave is eligible to be selected as a system clock reference
          When disabled, on receive side,
            -telecom slave does not pass the recovered clock to the system clock 
            -telecom slave does not process the QL from selected SOOC's clock class 
            -telecom slave is not eligible to be selected as a 
                     system clock reference."
     ::= { f3PtpTSEntry 13 }

f3PtpTSClockQLModeEnabled OBJECT-TYPE 
    SYNTAX     TruthValue
    MAX-ACCESS read-write
    STATUS     current
    DESCRIPTION
         "This object allows to specify whether the Telecom Slave 
          can be enabled/disabled for QL Mode.  
          When enabled, on receive side 
            -telecom slave can extract the QL from selected SOOC's clock class 
          When disabled, on receive side,
            -telecom slave does not process the QL from selected SOOC's clock class."
     ::= { f3PtpTSEntry 14 }

f3PtpTSClockExpectedQL OBJECT-TYPE 
    SYNTAX     SSMQualityLevel
    MAX-ACCESS read-write
    STATUS     current
    DESCRIPTION
         "This object allows to specify the expected QL when the 
          Telecom Slave is enabled for QL Mode.  This is applicable 
          when f3PtpTSClockQLModeEnabled is set to true.
          This object allows the user to set a minimum
          expected received Quality Level on the Telecom Slave. 
          The valid values depend upon the SYNC entity's Network Clock Type. 
          A value of None represents that a minimum Quality Level is not expected. 
          The default value shall be None."
     ::= { f3PtpTSEntry 15 }

f3PtpTSClockAssumedQL OBJECT-TYPE 
    SYNTAX     SSMQualityLevel
    MAX-ACCESS read-write
    STATUS     current
    DESCRIPTION
         "This object allows to specify the assumed QL on the 
          Telecom Slave.  The Assumed QL is only meaningful if the Network Clock Type
          (see fsp150cm-sync.mib) is option1 and the 
          telecom slave's QL Mode is disabled and the telecom slave is being used as 
          an input reference source. Under these conditions,
          the specified QL value is assumed to be the Quality Level of the
          non-failed reference."
     ::= { f3PtpTSEntry 16 }

f3PtpTSClockReceivedQL OBJECT-TYPE 
    SYNTAX     SSMQualityLevel
    MAX-ACCESS read-only
    STATUS     current
    DESCRIPTION
         "This object provides the Received QL value for the Telecom Slave. 
          If the Telecom Slave's QL Mode is disabled, then the received 
          QL value is not applicable."
     ::= { f3PtpTSEntry 17 }

f3PtpTSStorageType OBJECT-TYPE
    SYNTAX     StorageType
    MAX-ACCESS read-create
    STATUS     current
    DESCRIPTION
            "The type of storage configured for this entry."
    ::= { f3PtpTSEntry 18 }

f3PtpTSRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTSRowStatus supported are
            createAndGo(4) and destroy(6).  All mandatory attributes
            must be specified in a single SNMP SET request with
            f3PtpTSRowStatus value as createAndGo(4).
            Upon successful row creation, this object has a
            value of active(1).

            The f3PtpTSRowStatus object may be modified if
            the associated instance of this object is equal to active(1)."
    ::= { f3PtpTSEntry 19 }

f3PtpTSTimeTraceabilityStatus OBJECT-TYPE
    SYNTAX      TruthValue
    MAX-ACCESS  read-only
    STATUS      current
    DESCRIPTION
           "This object provides the Time traceability status of the
            Telecom Slave."
    ::= { f3PtpTSEntry 20 }

f3PtpTSTimeSinceTimeTraceabilityChanged OBJECT-TYPE
    SYNTAX      Unsigned32
    MAX-ACCESS  read-only
    STATUS      current
    DESCRIPTION
           "This object provides the time in seconds since the Time traceability 
            changed on the Telecom Slave."
    ::= { f3PtpTSEntry 21 }

f3PtpTSFreqTraceabilityStatus OBJECT-TYPE
    SYNTAX      TruthValue
    MAX-ACCESS  read-only
    STATUS      current
    DESCRIPTION
           "This object provides the Frequency traceability status of the
            Telecom Slave."
    ::= { f3PtpTSEntry 22 }

f3PtpTSTimeSinceFreqTraceabilityChanged OBJECT-TYPE
    SYNTAX      Unsigned32
    MAX-ACCESS  read-only
    STATUS      current
    DESCRIPTION
           "This object provides the time in seconds since the Frequency traceability 
            changed on the Telecom Slave."
    ::= { f3PtpTSEntry 23 }

f3PtpTSFreqRecoveryTarget OBJECT-TYPE
    SYNTAX      FreqRecoveryTarget
    MAX-ACCESS  read-write
    STATUS      current
    DESCRIPTION
           "This object provides the frequency recovery target." 
    ::= { f3PtpTSEntry 24 }

f3PtpTSCurrentCRScore OBJECT-TYPE
    SYNTAX      Unsigned32
    MAX-ACCESS  read-only
    STATUS      current
    DESCRIPTION
           "This object provides the current Clock Recovery Score."
    ::= { f3PtpTSEntry 25 }

f3PtpTSTimeLastCRScore OBJECT-TYPE
    SYNTAX      DateAndTime
    MAX-ACCESS  read-only
    STATUS      current
    DESCRIPTION
           "This object provides the time of the last Clock Recovery Score."
    ::= { f3PtpTSEntry 26 }

f3PtpTSTargetPhaseRecoveryAccuracy OBJECT-TYPE
    SYNTAX      Unsigned32
    MAX-ACCESS  read-write
    STATUS      current
    DESCRIPTION
           "This object allows specification of the expected Time of Day accuracy
            in nanoseconds."
    ::= { f3PtpTSEntry 27 }

f3PtpTSCurrentPRScore OBJECT-TYPE
    SYNTAX      Unsigned32
    MAX-ACCESS  read-only
    STATUS      current
    DESCRIPTION
           "This object provides the current Phase Recovery Score."
    ::= { f3PtpTSEntry 28 }

f3PtpTSTimeLastPRScore OBJECT-TYPE
    SYNTAX      DateAndTime
    MAX-ACCESS  read-only
    STATUS      current
    DESCRIPTION
           "This object provides the time of the last Phase Recovery Score."
    ::= { f3PtpTSEntry 29 }

f3PtpTSClockClass OBJECT-TYPE
    SYNTAX      Unsigned32
    MAX-ACCESS  read-only
    STATUS      deprecated
    DESCRIPTION
           "This object specify Telecome Slave clock class."
    ::= { f3PtpTSEntry 30 }

f3PtpTSClockAccuracy OBJECT-TYPE
    SYNTAX      Unsigned32
    MAX-ACCESS  read-only
    STATUS      current
    DESCRIPTION
           "This object specify Telecome Slave clock accuracy."
    ::= { f3PtpTSEntry 31 }

f3PtpTSTimeSource OBJECT-TYPE
    SYNTAX      TimeSource
    MAX-ACCESS  read-only
    STATUS      current
    DESCRIPTION
           "This object specify Telecome Slave time source."
    ::= { f3PtpTSEntry 32 }

f3PtpTSPhaseRecoveryState OBJECT-TYPE
    SYNTAX      PhaseRecoveryState
    MAX-ACCESS  read-only
    STATUS      current
    DESCRIPTION
           "This object specify the phase recovery state."
    ::= { f3PtpTSEntry 33 }

f3PtpTSTimeHoldoverAccuracy OBJECT-TYPE
    SYNTAX      HoldoverAccuracy
    MAX-ACCESS  read-write
    STATUS      current
    DESCRIPTION
           "This object specify the time hold over accuracy."
    ::= { f3PtpTSEntry 34 }

f3PtpTSWtrTime OBJECT-TYPE
    SYNTAX     Integer32 (0..12)
    MAX-ACCESS  read-write
    STATUS      current
    DESCRIPTION
           "This object should allow configuration of Wait To Restore timeout in minutes.
           The range of this object should be 0-12."
    ::= { f3PtpTSEntry 35 }

--
-- PTP Slave Only Ordinary Clock Table 
--
f3PtpSOOCTable OBJECT-TYPE
    SYNTAX     SEQUENCE OF F3PtpSOOCEntry 
    MAX-ACCESS not-accessible
    STATUS     current
    DESCRIPTION
         "A list of entries corresponding to the Slave Only Ordinary Clocks."
    ::= { f3PtpConfigObjects 4 }

f3PtpSOOCEntry OBJECT-TYPE
    SYNTAX     F3PtpSOOCEntry 
    MAX-ACCESS not-accessible
    STATUS     current
    DESCRIPTION
          "An entry containing information applicable to a particular
           Slave Only Ordinary Clock Entity."
    INDEX { neIndex, f3PtpTSIndex,  f3PtpSOOCIndex }
    ::= { f3PtpSOOCTable 1 }

F3PtpSOOCEntry ::= SEQUENCE {
    f3PtpSOOCIndex                               Integer32,

    f3PtpSOOCName                                DisplayString,
    f3PtpSOOCAlias                               DisplayString,

    f3PtpSOOCAdminState                          AdminState,
    f3PtpSOOCOperationalState                    OperationalState,
    f3PtpSOOCSecondaryState                      SecondaryState,

    f3PtpSOOCServiceFlow                         VariablePointer,
    f3PtpSOOCMasterClockType                     MasterClockType,
    f3PtpSOOCUnicastMessageNegEnabled            TruthValue,
    f3PtpSOOCMasterDelayMechanism                DelayMechanism,
    f3PtpSOOCMasterPriority                      Integer32,

    f3PtpSOOCMasterIpProtocol                    IpVersion,
    f3PtpSOOCSlaveIpV4Address                    IpAddress,
    f3PtpSOOCSlaveIpV4SubnetMask                 IpAddress,
    f3PtpSOOCMasterIpV4Address                   IpAddress,
    f3PtpSOOCIpPriorityMapMode                   IpPriorityMapMode,
    f3PtpSOOCIpPriority                          Integer32,

    f3PtpSOOCMasterLeaseDuration                 Integer32,

    f3PtpSOOCMasterAnnounceMsgRate               AnnounceMsgRate,
    f3PtpSOOCMasterAnnounceMsgReceiptTimeout     Integer32,

    f3PtpSOOCMasterSyncMsgRate                   SyncMsgRate,
    f3PtpSOOCMasterSyncReceiptTimeout            Integer32,

    f3PtpSOOCMasterDelayRspMsgRate               DelayRespMsgRate,
    f3PtpSOOCMasterDelayRspReceiptTimeout        Integer32,

    f3PtpSOOCMasterRequestUnicastTimeout         Integer32,
    f3PtpSOOCMasterRequestUnicastRestartTimer    Integer32,

    f3PtpSOOCCurrentOffsetFromMaster             ScaledNanoseconds,
    f3PtpSOOCAnnounceMsgClockClass               Integer32,
    f3PtpSOOCLastReceivedAnnounceMsg             OCTET STRING,
    f3PtpSOOCLastReceivedSyncMsg                 OCTET STRING,
    f3PtpSOOCLastReceivedDelayRspMsg             OCTET STRING,

    f3PtpSOOCRecentMeanPathDelay                 ScaledNanoseconds,
    f3PtpSOOCRecentSyncPDV                       ScaledNanoseconds,

    f3PtpSOOCStorageType                         StorageType,
    f3PtpSOOCRowStatus                           RowStatus,

    f3PtpSOOCRecentSyncPathDelay                 ScaledNanoseconds,

    f3PtpSOOCSoocProtectionState                 PTPProtectionState,
    f3PtpSOOCSoocWtr                             TruthValue,
    f3PtpSOOCSoocClockClass                      Unsigned32,
    f3PtpSOOCSoocClockRecoveryState              ClockRecoveryState,
    f3PtpSOOCSoocPhaseRecoveryState              PhaseRecoveryState,
    f3PtpSOOCE2eDelayAsymmetryComp               CompensationMode,
    f3PtpSOOCE2eAutoAsymmetryCompStatus          CompensationStatus,
    f3PtpSOOCE2eDelayAsymmetry                   Integer32,
    f3PtpSOOCSoocLockOutControl                  TruthValue,
    f3PtpSOOCSlaveIpV6Address                    Ipv6Address,             
    f3PtpSOOCSlaveIpV6AddrPrefixLength           Integer32,
    f3PtpSOOCMasterIpV6Address                   Ipv6Address,
    f3PtpSOOCMinimumExpectedClockClass           Integer32,
    f3PtpSOOCMasterMessageMode                   SlaveMode,

    f3PtpSOOCDefaultGatewayControl               ToggleValue,
    f3PtpSOOCGateway                             IpAddress,
    f3PtpSOOCIpV6Gateway                         Ipv6Address,
    f3PtpSOOCAlgorithmPtpAware                   TruthValue


}

f3PtpSOOCIndex OBJECT-TYPE
    SYNTAX     Integer32
    MAX-ACCESS not-accessible 
    STATUS     current
    DESCRIPTION
         "Unique index value associated with the Slave Only Ordinary Clock."
     ::= { f3PtpSOOCEntry 1 }

f3PtpSOOCName    OBJECT-TYPE
    SYNTAX       DisplayString (SIZE(1..15))
    MAX-ACCESS   read-create
    STATUS       current
    DESCRIPTION
         "This object allows SNMP management entities to provide a
          name to the Slave Only Ordinary Clock.  This is used
          for creation of the underlying IP Interface associated 
          with the SOOC."
     ::= { f3PtpSOOCEntry 2 }

f3PtpSOOCAlias    OBJECT-TYPE
    SYNTAX      DisplayString (SIZE(0..256))
    MAX-ACCESS  read-create
    STATUS      current
    DESCRIPTION
         "This object allows SNMP management entities to provide an 
          alias to the Slave Only Ordinary Clock."
     ::= { f3PtpSOOCEntry 3 }

f3PtpSOOCAdminState OBJECT-TYPE
    SYNTAX      AdminState 
    MAX-ACCESS  read-write
    STATUS      current
    DESCRIPTION
            "This object represents the Administrative State of the Slave Only 
             Ordinary Clock."
     ::= { f3PtpSOOCEntry 4 }

f3PtpSOOCOperationalState   OBJECT-TYPE
    SYNTAX      OperationalState 
    MAX-ACCESS  read-only
    STATUS      current
    DESCRIPTION
            "This object represents the Operational State of the Slave Only 
             Ordinary Clock."
     ::= { f3PtpSOOCEntry 5 }

f3PtpSOOCSecondaryState     OBJECT-TYPE
    SYNTAX      SecondaryState 
    MAX-ACCESS  read-only
    STATUS      current
    DESCRIPTION
           "This object represents the Secondary State of the Slave Only
            Ordinary Clock."
     ::= { f3PtpSOOCEntry 6 }

f3PtpSOOCServiceFlow OBJECT-TYPE
    SYNTAX     VariablePointer
    MAX-ACCESS read-create 
    STATUS     current
    DESCRIPTION
         "Traffic Flow or SHG associated with the Slave Only Ordinary Clock."
     ::= { f3PtpSOOCEntry 7 }

f3PtpSOOCMasterClockType OBJECT-TYPE
    SYNTAX     MasterClockType
    MAX-ACCESS read-only 
    STATUS     current
    DESCRIPTION
         "This object must be used to specify the type of the Master Clock."
     ::= { f3PtpSOOCEntry 8 }

f3PtpSOOCUnicastMessageNegEnabled OBJECT-TYPE
    SYNTAX     TruthValue
    MAX-ACCESS read-create 
    STATUS     current
    DESCRIPTION
         "This object must be used to specify whether Unicast Message
          Negotiation is enabled for the Master Clock."
     ::= { f3PtpSOOCEntry 9 }

f3PtpSOOCMasterDelayMechanism OBJECT-TYPE
    SYNTAX     DelayMechanism
    MAX-ACCESS read-write 
    STATUS     current
    DESCRIPTION
         "This object allows specification of the delay mechanism." 
     ::= { f3PtpSOOCEntry 10 }

f3PtpSOOCMasterPriority OBJECT-TYPE
    SYNTAX     Integer32
    MAX-ACCESS read-create 
    STATUS     current
    DESCRIPTION
         "This object allows specification of the OC Master Priority."
     ::= { f3PtpSOOCEntry 11 }

f3PtpSOOCMasterIpProtocol OBJECT-TYPE
    SYNTAX     IpVersion
    MAX-ACCESS read-create 
    STATUS     current
    DESCRIPTION
         "This object allows specification of the IP Protocol to
          communicate with the OC Master.  Only ipv4 is supported."
     ::= { f3PtpSOOCEntry 12 }

f3PtpSOOCSlaveIpV4Address OBJECT-TYPE
    SYNTAX     IpAddress
    MAX-ACCESS read-create 
    STATUS     current
    DESCRIPTION
         "This object allows specification of the IPv4 Address of
          the Slave Only Ordinary Clock."
     ::= { f3PtpSOOCEntry 13 }

f3PtpSOOCSlaveIpV4SubnetMask OBJECT-TYPE
    SYNTAX     IpAddress
    MAX-ACCESS read-create 
    STATUS     current
    DESCRIPTION
         "This object allows specification of the IPv4 Subnet Mask of
          the Slave Only Ordinary Clock."
     ::= { f3PtpSOOCEntry 14 }

f3PtpSOOCMasterIpV4Address OBJECT-TYPE
    SYNTAX     IpAddress
    MAX-ACCESS read-create 
    STATUS     current
    DESCRIPTION
         "This object allows specification of the IPv4 Address of
          the OC Master."
     ::= { f3PtpSOOCEntry 15 }

f3PtpSOOCIpPriorityMapMode  OBJECT-TYPE
    SYNTAX     IpPriorityMapMode 
    MAX-ACCESS read-write
    STATUS     current
    DESCRIPTION
         "This object enables specification of Priority Mapping Mode for
          the Slave Only Ordinary Clock."
     ::= { f3PtpSOOCEntry 16 }

f3PtpSOOCIpPriority  OBJECT-TYPE
    SYNTAX     Integer32 (0..63)
    MAX-ACCESS read-write
    STATUS     current
    DESCRIPTION
         "This object enables specification of Priority Value for
          f3PtpSOOCIpPriorityMapMode as priomap-tos,priomap-dscp."
     ::= { f3PtpSOOCEntry 17 }

f3PtpSOOCMasterLeaseDuration OBJECT-TYPE
    SYNTAX     Integer32
    MAX-ACCESS read-create
    STATUS     current
    DESCRIPTION
        "This object allows specification of the lease Duration for Announce and Sync
         messages." 
     ::= { f3PtpSOOCEntry 18 }

f3PtpSOOCMasterAnnounceMsgRate OBJECT-TYPE
    SYNTAX     AnnounceMsgRate
    MAX-ACCESS read-create
    STATUS     current
    DESCRIPTION
         "This object allows specification of the PTP Announce Message Rate."
     ::= { f3PtpSOOCEntry 19 }

f3PtpSOOCMasterAnnounceMsgReceiptTimeout OBJECT-TYPE
    SYNTAX     Integer32
    MAX-ACCESS read-create
    STATUS     current
    DESCRIPTION
        "This object allows specification of the PTP Announce Message 
         Receipt Timeout."
     ::= { f3PtpSOOCEntry 20 }

f3PtpSOOCMasterSyncMsgRate OBJECT-TYPE
    SYNTAX     SyncMsgRate
    MAX-ACCESS read-create
    STATUS     current
    DESCRIPTION
        "This object allows specification of the PTP Sync 
         Message Rate." 
     ::= { f3PtpSOOCEntry 21 }

f3PtpSOOCMasterSyncReceiptTimeout OBJECT-TYPE
    SYNTAX     Integer32
    MAX-ACCESS read-create
    STATUS     current
    DESCRIPTION
        "This object allows specification of the PTP Sync Message 
         Receipt Timeout."
     ::= { f3PtpSOOCEntry 22 }

f3PtpSOOCMasterDelayRspMsgRate OBJECT-TYPE
    SYNTAX     DelayRespMsgRate
    MAX-ACCESS read-create
    STATUS     current
    DESCRIPTION
        "This object allows specification of the PTP Delay Response 
         Message Rate." 
     ::= { f3PtpSOOCEntry 23 }

f3PtpSOOCMasterDelayRspReceiptTimeout OBJECT-TYPE
    SYNTAX     Integer32
    MAX-ACCESS read-create
    STATUS     current
    DESCRIPTION
        "This object allows specification of the PTP Delay Response 
         Message Receipt Timeout."
     ::= { f3PtpSOOCEntry 24 }

f3PtpSOOCMasterRequestUnicastTimeout  OBJECT-TYPE 
    SYNTAX     Integer32
    MAX-ACCESS read-write
    STATUS     current
    DESCRIPTION
        "This object allows specification of the Request Unicast 
         Timeout in seconds.  Unicast transmission is termed as
         failed when this timeout occurs."
     ::= { f3PtpSOOCEntry 25 }

f3PtpSOOCMasterRequestUnicastRestartTimer  OBJECT-TYPE 
    SYNTAX     Integer32
    MAX-ACCESS read-write
    STATUS     current
    DESCRIPTION
        "This object allows specification of the time (in seconds) to wait
         to restart the Request Unicast signalling." 
     ::= { f3PtpSOOCEntry 26 }

f3PtpSOOCCurrentOffsetFromMaster OBJECT-TYPE
    SYNTAX     ScaledNanoseconds 
    MAX-ACCESS read-only
    STATUS     current
    DESCRIPTION
        "This object provides the current Offset From Master.
         The value provided is in nanoseconds." 
     ::= { f3PtpSOOCEntry 27 }

f3PtpSOOCAnnounceMsgClockClass OBJECT-TYPE
    SYNTAX     Integer32
    MAX-ACCESS read-only
    STATUS     deprecated
    DESCRIPTION
        "This object provides the Clock Class obtained in the
         Announce Message." 
     ::= { f3PtpSOOCEntry 28 }

f3PtpSOOCLastReceivedAnnounceMsg OBJECT-TYPE
    SYNTAX     OCTET STRING (SIZE(0..128))
    MAX-ACCESS read-only
    STATUS     current
    DESCRIPTION
        "This object provides the Last Received  
         Announce Message." 
     ::= { f3PtpSOOCEntry 29 }

f3PtpSOOCLastReceivedSyncMsg OBJECT-TYPE
    SYNTAX     OCTET STRING (SIZE(0..128))
    MAX-ACCESS read-only
    STATUS     current
    DESCRIPTION
        "This object provides the Last Received  
         Sync Message." 
     ::= { f3PtpSOOCEntry 30 }

f3PtpSOOCLastReceivedDelayRspMsg OBJECT-TYPE
    SYNTAX     OCTET STRING (SIZE(0..128))
    MAX-ACCESS read-only
    STATUS     current
    DESCRIPTION
        "This object provides the Last Received  
         Delay Response Message." 
     ::= { f3PtpSOOCEntry 31 }

f3PtpSOOCRecentMeanPathDelay OBJECT-TYPE
    SYNTAX     ScaledNanoseconds  
    MAX-ACCESS read-only
    STATUS     current
    DESCRIPTION
        "This object provides the most recent 
         mean path delay." 
     ::= { f3PtpSOOCEntry 32 }

f3PtpSOOCRecentSyncPDV OBJECT-TYPE
    SYNTAX     ScaledNanoseconds 
    MAX-ACCESS read-only
    STATUS     current
    DESCRIPTION
        "This object provides the Sync messages 
         packet delay variation."
     ::= { f3PtpSOOCEntry 33 }

f3PtpSOOCStorageType OBJECT-TYPE
    SYNTAX     StorageType
    MAX-ACCESS read-create
    STATUS     current
    DESCRIPTION
            "The type of storage configured for this entry."
    ::= { f3PtpSOOCEntry 34 }

f3PtpSOOCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpSOOCRowStatus supported are
            createAndGo(4) and destroy(6).  All mandatory attributes
            must be specified in a single SNMP SET request with
            f3PtpSOOCRowStatus value as createAndGo(4).
            Upon successful row creation, this object has a
            value of active(1).

            The f3PtpSOOCRowStatus object may be modified if
            the associated instance of this object is equal to active(1)."
    ::= { f3PtpSOOCEntry 35 }

f3PtpSOOCRecentSyncPathDelay OBJECT-TYPE
    SYNTAX     ScaledNanoseconds  
    MAX-ACCESS read-only
    STATUS     current
    DESCRIPTION
        "This object provides the Sync messages 
         packet delay."
     ::= { f3PtpSOOCEntry 36 }

f3PtpSOOCSoocProtectionState  OBJECT-TYPE 
    SYNTAX     PTPProtectionState
    MAX-ACCESS read-only
    STATUS     current
    DESCRIPTION
        "This object indicates whether the Sooc is used by 
        the Telecom Slave for the clock recovery."
     ::= { f3PtpSOOCEntry 37 }

f3PtpSOOCSoocWtr OBJECT-TYPE
    SYNTAX     TruthValue 
    MAX-ACCESS read-only
    STATUS     current
    DESCRIPTION
        "This object provides WTR protection state of the Sooc."
     ::= { f3PtpSOOCEntry 38 }

f3PtpSOOCSoocClockClass OBJECT-TYPE
    SYNTAX     Unsigned32
    MAX-ACCESS read-only
    STATUS     current
    DESCRIPTION
        "This object provides the Clock Class of the Sooc."
     ::= { f3PtpSOOCEntry 39 }

f3PtpSOOCSoocClockRecoveryState OBJECT-TYPE
    SYNTAX     ClockRecoveryState
    MAX-ACCESS read-only
    STATUS     current
    DESCRIPTION
        "This object provides the frequency recovery state
        of the Sooc."   
     ::= { f3PtpSOOCEntry 40 }

f3PtpSOOCSoocPhaseRecoveryState OBJECT-TYPE
    SYNTAX     PhaseRecoveryState
    MAX-ACCESS read-only
    STATUS     current
    DESCRIPTION
        "This object provides the Phase recovery state
        of the Sooc."   
     ::= { f3PtpSOOCEntry 41 }



f3PtpSOOCE2eDelayAsymmetryComp OBJECT-TYPE
    SYNTAX     CompensationMode
    MAX-ACCESS read-write
    STATUS     current
    DESCRIPTION
        "This object allows configuration of end to end asymmetry 
        delay compensation mode."   
     ::= { f3PtpSOOCEntry 42 }

f3PtpSOOCE2eAutoAsymmetryCompStatus OBJECT-TYPE
    SYNTAX     CompensationStatus  
    MAX-ACCESS read-only
    STATUS     current
    DESCRIPTION
        "This object provides the automatic end to end delay asymmetry 
        status." 
     ::= { f3PtpSOOCEntry 43 }

f3PtpSOOCE2eDelayAsymmetry OBJECT-TYPE
    SYNTAX     Integer32 
    MAX-ACCESS read-write
    STATUS     current
    DESCRIPTION
        "This object is used for manual configuration of end to end 
        delay asymmetry in ns if end to end delay asymmetry compensation is Manual.
        Or for indication of the measured delay asymmetry if
        end to end delay asymmetry compensation is automatic."
     ::= { f3PtpSOOCEntry 44 }

f3PtpSOOCSoocLockOutControl OBJECT-TYPE
    SYNTAX     TruthValue 
    MAX-ACCESS read-write
    STATUS     current
    DESCRIPTION
        "This object is used to specify whether Sooc
          Lockout operation is enabled for the Sooc."
     ::= { f3PtpSOOCEntry 45 }


f3PtpSOOCSlaveIpV6Address OBJECT-TYPE
    SYNTAX     Ipv6Address 
    MAX-ACCESS read-create
    STATUS   current
    DESCRIPTION
         "This object allows specification of the unicast IPv6 Address of
          the Slave Only Ordinary Clock."
    ::= { f3PtpSOOCEntry 46 }

f3PtpSOOCSlaveIpV6AddrPrefixLength OBJECT-TYPE
    SYNTAX     Integer32 (0..128)
    MAX-ACCESS read-create
    STATUS   current
    DESCRIPTION
       "This object allows specification of the unicast IPv6 Address prefix length of
          the Slave Only Ordinary Clock."
    ::= { f3PtpSOOCEntry 47 }

f3PtpSOOCMasterIpV6Address OBJECT-TYPE
    SYNTAX     Ipv6Address 
    MAX-ACCESS read-create
    STATUS   current
    DESCRIPTION
       "This object allows specification of the unicast IPv6 Address of
          the OC Master."
    ::= { f3PtpSOOCEntry 48 }

f3PtpSOOCMinimumExpectedClockClass  OBJECT-TYPE 
    SYNTAX     Integer32 (0..255)
    MAX-ACCESS read-write
    STATUS     current
    DESCRIPTION
        "This object allows setting the minimum expected clock class value,
     which setes the minimum threshold for receiving packets.
     if the received clock clock class is greater than the expected
     clock class value, the packets for the grandmaster or boundary clock that
     are sending this clock class are dropped.
     In addition, an alarm called clock-class-mismatch is generated. The default is 247."
     ::= { f3PtpSOOCEntry 49 }

f3PtpSOOCMasterMessageMode  OBJECT-TYPE 
    SYNTAX     SlaveMode
    MAX-ACCESS read-write
    STATUS     current
    DESCRIPTION
        "Describes the PTP slave mode on OSA540X."
     ::= { f3PtpSOOCEntry 50 }

f3PtpSOOCDefaultGatewayControl OBJECT-TYPE
    SYNTAX     ToggleValue
    MAX-ACCESS read-create
    STATUS     current
    DESCRIPTION
         "This attribute control Gatwaye address for Slave Only Ordinary Clock."
     ::= { f3PtpSOOCEntry 51 }

f3PtpSOOCGateway OBJECT-TYPE
    SYNTAX     IpAddress
    MAX-ACCESS read-create 
    STATUS     current
    DESCRIPTION
         "This object allows specification of the IPv4 Gateway Address of
          Slave Only Ordinary Clock."
     ::= { f3PtpSOOCEntry 52 }

f3PtpSOOCIpV6Gateway OBJECT-TYPE
    SYNTAX     Ipv6Address 
    MAX-ACCESS read-create
    STATUS   current
    DESCRIPTION
         "This object allows specification of the IPv6 Gateway Address of
          Slave Only Ordinary Clock."
    ::= { f3PtpSOOCEntry 53 }

f3PtpSOOCAlgorithmPtpAware OBJECT-TYPE
    SYNTAX     TruthValue 
    MAX-ACCESS read-write
    STATUS   current
    DESCRIPTION
         "This object allows specification of the slave algorithm mode - PTP aware or unaware."
    ::= { f3PtpSOOCEntry 54 }

--
-- PTP Ordinary Clock Slave Virtual Port Table 
--
f3PtpOCSlaveVirtualPortTable OBJECT-TYPE
    SYNTAX     SEQUENCE OF F3PtpOCSlaveVirtualPortEntry 
    MAX-ACCESS not-accessible
    STATUS     current
    DESCRIPTION
         "A list of entries corresponding to the PTP Transparent 
          Clock Virtual Ports."
    ::= { f3PtpConfigObjects 5 }

f3PtpOCSlaveVirtualPortEntry OBJECT-TYPE
    SYNTAX     F3PtpOCSlaveVirtualPortEntry
    MAX-ACCESS not-accessible
    STATUS     current
    DESCRIPTION
          "An entry containing information applicable to a particular
           PTP OCSlave Virtual Port Entity."
    INDEX { neIndex, f3PtpTSIndex,  
                     f3PtpSOOCIndex, f3PtpOCSlaveVirtualPortIndex }
    ::= { f3PtpOCSlaveVirtualPortTable 1 }

F3PtpOCSlaveVirtualPortEntry ::= SEQUENCE {
    f3PtpOCSlaveVirtualPortIndex              Integer32,

    f3PtpOCSlaveVirtualPortAlias              DisplayString,

    f3PtpOCSlaveVirtualPortAdminState         AdminState,
    f3PtpOCSlaveVirtualPortOperationalState   OperationalState,
    f3PtpOCSlaveVirtualPortSecondaryState     SecondaryState,

    f3PtpOCSlaveVirtualPortIdentity           PortIdentity,
    f3PtpOCSlaveVirtualPortFlowPoint          VariablePointer,
    f3PtpOCSlaveVirtualPortState              PtpPortState,
    f3PtpOCSlaveVirtualPortStorageType        StorageType,
    f3PtpOCSlaveVirtualPortRowStatus          RowStatus
}

f3PtpOCSlaveVirtualPortIndex OBJECT-TYPE
    SYNTAX     Integer32
    MAX-ACCESS not-accessible 
    STATUS     current
    DESCRIPTION
         "Unique index value associated with the PTP OC Slave 
          Virtual Port index."
     ::= { f3PtpOCSlaveVirtualPortEntry 1 }

f3PtpOCSlaveVirtualPortAlias OBJECT-TYPE
    SYNTAX      DisplayString (SIZE(0..256))
    MAX-ACCESS  read-create
    STATUS      current
    DESCRIPTION
         "This object allows SNMP management entities to provide an 
          alias to the OC Slave Virtual Port entity."
     ::= { f3PtpOCSlaveVirtualPortEntry 2 }

f3PtpOCSlaveVirtualPortAdminState OBJECT-TYPE
    SYNTAX      AdminState 
    MAX-ACCESS  read-write
    STATUS      current
    DESCRIPTION
            "This object represents the Administrative State of the 
             OC Slave Virtual Port."
    ::= { f3PtpOCSlaveVirtualPortEntry 3 }

f3PtpOCSlaveVirtualPortOperationalState   OBJECT-TYPE
    SYNTAX      OperationalState 
    MAX-ACCESS  read-only
    STATUS      current
    DESCRIPTION
            "This object represents the Operational State of the OC Slave 
             Virtual Port."
    ::= { f3PtpOCSlaveVirtualPortEntry 4 }

f3PtpOCSlaveVirtualPortSecondaryState     OBJECT-TYPE
    SYNTAX      SecondaryState 
    MAX-ACCESS  read-only
    STATUS      current
    DESCRIPTION
           "This object represents the Secondary State of the OC Slave
            Virtual Port." 
    ::= { f3PtpOCSlaveVirtualPortEntry 5 }

f3PtpOCSlaveVirtualPortIdentity OBJECT-TYPE
    SYNTAX     PortIdentity 
    MAX-ACCESS read-write
    STATUS     current
    DESCRIPTION
         "This object represents the PTP Port Identity of the 
                       OC Slave Virtual Port." 
     ::= { f3PtpOCSlaveVirtualPortEntry 6 }

f3PtpOCSlaveVirtualPortFlowPoint OBJECT-TYPE
    SYNTAX     VariablePointer 
    MAX-ACCESS read-create
    STATUS     current
    DESCRIPTION
         "This object associates the PTP Flow Point with the 
          Slave Only Ordinary Clock."
     ::= { f3PtpOCSlaveVirtualPortEntry 7 }

f3PtpOCSlaveVirtualPortState OBJECT-TYPE
    SYNTAX     PtpPortState 
    MAX-ACCESS read-only
    STATUS     current
    DESCRIPTION
         "This object provides the PTP state of the OC Slave Virtual Port." 
     ::= { f3PtpOCSlaveVirtualPortEntry 8 }

f3PtpOCSlaveVirtualPortStorageType OBJECT-TYPE
    SYNTAX     StorageType
    MAX-ACCESS read-create
    STATUS     current
    DESCRIPTION
            "The type of storage configured for this entry."
    ::= { f3PtpOCSlaveVirtualPortEntry 9 }

f3PtpOCSlaveVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpOCSlaveVirtualPortRowStatus supported are
            createAndGo(4) and destroy(6).  All mandatory attributes
            must be specified in a single SNMP SET request with
            f3PtpOCSlaveVirtualPortRowStatus value as createAndGo(4).
            Upon successful row creation, this object has a
            value of active(1).

            The f3PtpOCSlaveVirtualPortRowStatus object may be modified if
            the associated instance of this object is equal to active(1)."
    ::= { f3PtpOCSlaveVirtualPortEntry 10 }

--
-- Ethernet Access Port - PTP Flow Point Table 
--
f3PtpAccPortFlowPointTable OBJECT-TYPE
    SYNTAX     SEQUENCE OF F3PtpAccPortFlowPointEntry 
    MAX-ACCESS not-accessible
    STATUS     current
    DESCRIPTION
       "A list of entries corresponding to the PTP Access Port Flow Point
        entities."
    ::= { f3PtpConfigObjects 6 }

f3PtpAccPortFlowPointEntry OBJECT-TYPE
    SYNTAX     F3PtpAccPortFlowPointEntry
    MAX-ACCESS not-accessible
    STATUS     current
    DESCRIPTION
          "An entry containing information applicable to a particular
           Access Port Flow Point Entity."
    INDEX { neIndex, shelfIndex, slotIndex, cmEthernetAccPortIndex, 
            f3PtpAccPortFlowPointIndex }
    ::= { f3PtpAccPortFlowPointTable 1 }

F3PtpAccPortFlowPointEntry ::= SEQUENCE {
    f3PtpAccPortFlowPointIndex                 Integer32,

    f3PtpAccPortFlowPointAlias                 DisplayString,

    f3PtpAccPortFlowPointAdminState            AdminState,
    f3PtpAccPortFlowPointOperationalState      OperationalState,
    f3PtpAccPortFlowPointSecondaryState        SecondaryState,

    f3PtpAccPortFlowPointType                  PtpFlowPointType,
    f3PtpAccPortFlowPointClock                 VariablePointer,
    f3PtpAccPortFlowPointService               VariablePointer,
    f3PtpAccPortFlowPointOuterVlanEtherType    Integer32,
    f3PtpAccPortFlowPointOuterVlanMemberList   DisplayString,
    f3PtpAccPortFlowPointOuterUntaggedEnabled  TruthValue,
    f3PtpAccPortFlowPointInner1VlanEtherType   Integer32,
    f3PtpAccPortFlowPointInner1VlanMemberList  DisplayString,
    f3PtpAccPortFlowPointInner1UntaggedEnabled TruthValue,
    f3PtpAccPortFlowPointInner2VlanEtherType   Integer32,
    f3PtpAccPortFlowPointInner2VlanMemberList  DisplayString,
    f3PtpAccPortFlowPointInner2UntaggedEnabled TruthValue,

    f3PtpAccPortFlowPointStorageType           StorageType,
    f3PtpAccPortFlowPointRowStatus             RowStatus,
    f3PtpAccPortFlowPointCOS                   Integer32,
    f3PtpAccPortFlowPointCIRLo                 Unsigned32,
    f3PtpAccPortFlowPointCIRHi                 Unsigned32,
    f3PtpAccPortFlowPointEIRLo                 Unsigned32,
    f3PtpAccPortFlowPointEIRHi                 Unsigned32,
    f3PtpAccPortFlowPointBufferSize            Unsigned32,
    f3PtpAccPortFlowPointLoopAvoidance         VariablePointer,
    f3PtpAccPortFlowPointRefConnectGuardFlow   VariablePointer,
    f3PtpAccPortFlowPointSecureState           FlowSecState,
    f3PtpAccPortFlowPointSecureBlockingEnabled TruthValue
}

f3PtpAccPortFlowPointIndex OBJECT-TYPE
    SYNTAX     Integer32
    MAX-ACCESS not-accessible 
    STATUS     current
    DESCRIPTION
         "Unique index value associated with the Access Port PTP Flow Point."
     ::= { f3PtpAccPortFlowPointEntry 1 }

f3PtpAccPortFlowPointAlias OBJECT-TYPE
    SYNTAX      DisplayString (SIZE(0..256))
    MAX-ACCESS  read-create
    STATUS      current
    DESCRIPTION
         "This object allows SNMP management entities to provide an 
          alias to the Access Port PTP Flow Point."
     ::= { f3PtpAccPortFlowPointEntry 2 }

f3PtpAccPortFlowPointAdminState OBJECT-TYPE
    SYNTAX      AdminState 
    MAX-ACCESS  read-write
    STATUS      current
    DESCRIPTION
            "This object represents the Administrative State of the 
             PTP Flow Point." 
     ::= { f3PtpAccPortFlowPointEntry 3 }

f3PtpAccPortFlowPointOperationalState   OBJECT-TYPE
    SYNTAX      OperationalState 
    MAX-ACCESS  read-only
    STATUS      current
    DESCRIPTION
            "This object represents the Operational State of the PTP Flow 
             Point."
     ::= { f3PtpAccPortFlowPointEntry 4 }

f3PtpAccPortFlowPointSecondaryState     OBJECT-TYPE
    SYNTAX      SecondaryState 
    MAX-ACCESS  read-only
    STATUS      current
    DESCRIPTION
           "This object represents the Secondary State of the PTP Flow Point."
     ::= { f3PtpAccPortFlowPointEntry 5 }

f3PtpAccPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpAccPortFlowPointEntry 6 }

f3PtpAccPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpAccPortFlowPointEntry 7 }

f3PtpAccPortFlowPointService OBJECT-TYPE
    SYNTAX      VariablePointer 
    MAX-ACCESS  read-create
    STATUS      current
    DESCRIPTION
            "This object points to the associated Traffic Service Flow."
    ::= { f3PtpAccPortFlowPointEntry 8 }

f3PtpAccPortFlowPointOuterVlanEtherType OBJECT-TYPE
    SYNTAX      Integer32 
    MAX-ACCESS  read-create
    STATUS      current
    DESCRIPTION
            "This object allows specification of the Outer VLAN Ether Type
             of the PTP Flow."
    ::= { f3PtpAccPortFlowPointEntry 9 }

f3PtpAccPortFlowPointOuterVlanMemberList OBJECT-TYPE
    SYNTAX      DisplayString 
    MAX-ACCESS  read-create
    STATUS      current
    DESCRIPTION
            "This object allows specification of the Outer VLAN(s) 
             of the PTP Flow."
    ::= { f3PtpAccPortFlowPointEntry 10 }

f3PtpAccPortFlowPointOuterUntaggedEnabled OBJECT-TYPE
    SYNTAX      TruthValue 
    MAX-ACCESS  read-create
    STATUS      current
    DESCRIPTION
            "This object allows specification of whether the Outer VLAN
             exists or not." 
    ::= { f3PtpAccPortFlowPointEntry 11 }

f3PtpAccPortFlowPointInner1VlanEtherType OBJECT-TYPE
    SYNTAX      Integer32 
    MAX-ACCESS  read-create
    STATUS      current
    DESCRIPTION
            "This object allows specification of the Inner1 VLAN Ether Type
             of the PTP Flow."
    ::= { f3PtpAccPortFlowPointEntry 12 }

f3PtpAccPortFlowPointInner1VlanMemberList OBJECT-TYPE
    SYNTAX      DisplayString 
    MAX-ACCESS  read-create
    STATUS      current
    DESCRIPTION
            "This object allows specification of the Inner1 VLAN(s) 
             of the PTP Flow."
    ::= { f3PtpAccPortFlowPointEntry 13 }

f3PtpAccPortFlowPointInner1UntaggedEnabled OBJECT-TYPE
    SYNTAX      TruthValue 
    MAX-ACCESS  read-create
    STATUS      current
    DESCRIPTION
            "This object allows specification of whether the Inner1 VLAN
             exists or not." 
    ::= { f3PtpAccPortFlowPointEntry 14 }

f3PtpAccPortFlowPointInner2VlanEtherType OBJECT-TYPE
    SYNTAX      Integer32 
    MAX-ACCESS  read-create
    STATUS      current
    DESCRIPTION
            "This object allows specification of the Inner2 VLAN Ether Type
             of the PTP Flow."
    ::= { f3PtpAccPortFlowPointEntry 15 }

f3PtpAccPortFlowPointInner2VlanMemberList OBJECT-TYPE
    SYNTAX      DisplayString 
    MAX-ACCESS  read-create
    STATUS      current
    DESCRIPTION
            "This object allows specification of the Inner2 VLAN(s) 
             of the PTP Flow."
    ::= { f3PtpAccPortFlowPointEntry 16 }

f3PtpAccPortFlowPointInner2UntaggedEnabled OBJECT-TYPE
    SYNTAX      TruthValue 
    MAX-ACCESS  read-create
    STATUS      current
    DESCRIPTION
            "This object allows specification of whether the Inner1 VLAN
             exists or not." 
    ::= { f3PtpAccPortFlowPointEntry 17 }

f3PtpAccPortFlowPointStorageType OBJECT-TYPE
    SYNTAX     StorageType
    MAX-ACCESS read-create
    STATUS     current
    DESCRIPTION
            "The type of storage configured for this entry."
    ::= { f3PtpAccPortFlowPointEntry 18 }

f3PtpAccPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpAccPortFlowPointRowStatus supported are
            createAndGo(4) and destroy(6).  All mandatory attributes
            must be specified in a single SNMP SET request with
            f3PtpAccPortFlowPointRowStatus value as createAndGo(4).
            Upon successful row creation, this object has a
            value of active(1).

            The f3PtpAccPortFlowPointRowStatus object may be modified if
            the associated instance of this object is equal to active(1)."
    ::= { f3PtpAccPortFlowPointEntry 19 }


f3PtpAccPortFlowPointCOS OBJECT-TYPE
    SYNTAX      Integer32 (0..7)
    MAX-ACCESS  read-create
    STATUS      current
    DESCRIPTION
            "This object allows specification of Class of Service of the PTP traffic
             associated with this Flow Point."
    ::= { f3PtpAccPortFlowPointEntry 20 }

f3PtpAccPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpAccPortFlowPointEntry 21 }

f3PtpAccPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpAccPortFlowPointEntry 22 }

f3PtpAccPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpAccPortFlowPointEntry 23 }

f3PtpAccPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpAccPortFlowPointEntry 24 }

f3PtpAccPortFlowPointBufferSize OBJECT-TYPE
    SYNTAX      Unsigned32
    MAX-ACCESS  read-create
    STATUS      current
    DESCRIPTION
            "This object allows specification the Buffer Size of the queue associated
             with this Flow Point."
    ::= { f3PtpAccPortFlowPointEntry 25 }

f3PtpAccPortFlowPointLoopAvoidance OBJECT-TYPE
    SYNTAX      VariablePointer
    MAX-ACCESS  read-create
    STATUS      current
    DESCRIPTION
            "This object allows specify OID of this associated Loop Avoidance protocol entity."
    ::= { f3PtpAccPortFlowPointEntry 26 }

f3PtpAccPortFlowPointRefConnectGuardFlow OBJECT-TYPE
    SYNTAX      VariablePointer
    MAX-ACCESS  read-write
    STATUS      current
    DESCRIPTION
           "This object specifies Mac Sec flow object OID."
    ::= { f3PtpAccPortFlowPointEntry 27 }

f3PtpAccPortFlowPointSecureState OBJECT-TYPE
    SYNTAX      FlowSecState
    MAX-ACCESS  read-only
    STATUS      current
    DESCRIPTION
           "This object specifies the secure state of this flow."
    ::= { f3PtpAccPortFlowPointEntry 28 }

f3PtpAccPortFlowPointSecureBlockingEnabled OBJECT-TYPE
    SYNTAX      TruthValue
    MAX-ACCESS  read-write
    STATUS      current
    DESCRIPTION
           "This object can be used to enable/disable secure block."
    ::= { f3PtpAccPortFlowPointEntry 29 }


--
-- Ethernet Network Port - PTP Flow Point Table 
--
f3PtpNetPortFlowPointTable OBJECT-TYPE
    SYNTAX     SEQUENCE OF F3PtpNetPortFlowPointEntry 
    MAX-ACCESS not-accessible
    STATUS     current
    DESCRIPTION
       "A list of entries corresponding to the PTP Network Port Flow Point
        entities."
    ::= { f3PtpConfigObjects 7 }

f3PtpNetPortFlowPointEntry OBJECT-TYPE
    SYNTAX     F3PtpNetPortFlowPointEntry
    MAX-ACCESS not-accessible
    STATUS     current
    DESCRIPTION
          "An entry containing information applicable to a particular
           Network Port Flow Point Entity."
    INDEX { neIndex, shelfIndex, slotIndex, cmEthernetNetPortIndex, 
            f3PtpNetPortFlowPointIndex }
    ::= { f3PtpNetPortFlowPointTable 1 }


F3PtpNetPortFlowPointEntry ::= SEQUENCE {
    f3PtpNetPortFlowPointIndex                 Integer32,

    f3PtpNetPortFlowPointAlias                 DisplayString,

    f3PtpNetPortFlowPointAdminState            AdminState,
    f3PtpNetPortFlowPointOperationalState      OperationalState,
    f3PtpNetPortFlowPointSecondaryState        SecondaryState,

    f3PtpNetPortFlowPointType                  PtpFlowPointType,
    f3PtpNetPortFlowPointClock                 VariablePointer,
    f3PtpNetPortFlowPointService               VariablePointer,
    f3PtpNetPortFlowPointOuterVlanEtherType    Integer32,
    f3PtpNetPortFlowPointOuterVlanMemberList   DisplayString,
    f3PtpNetPortFlowPointOuterUntaggedEnabled  TruthValue,
    f3PtpNetPortFlowPointInner1VlanEtherType   Integer32,
    f3PtpNetPortFlowPointInner1VlanMemberList  DisplayString,
    f3PtpNetPortFlowPointInner1UntaggedEnabled TruthValue,
    f3PtpNetPortFlowPointInner2VlanEtherType   Integer32,
    f3PtpNetPortFlowPointInner2VlanMemberList  DisplayString,
    f3PtpNetPortFlowPointInner2UntaggedEnabled TruthValue,

    f3PtpNetPortFlowPointStorageType           StorageType,
    f3PtpNetPortFlowPointRowStatus             RowStatus,
    f3PtpNetPortFlowPointCOS                   Integer32,
    f3PtpNetPortFlowPointCIRLo                 Unsigned32,
    f3PtpNetPortFlowPointCIRHi                 Unsigned32,
    f3PtpNetPortFlowPointEIRLo                 Unsigned32,
    f3PtpNetPortFlowPointEIRHi                 Unsigned32,
    f3PtpNetPortFlowPointBufferSize            Unsigned32,
    f3PtpNetPortFlowPointLoopAvoidance         VariablePointer,
    f3PtpNetPortFlowPointRefConnectGuardFlow   VariablePointer,
    f3PtpNetPortFlowPointSecureState           FlowSecState,
    f3PtpNetPortFlowPointSecureBlockingEnabled TruthValue
}

f3PtpNetPortFlowPointIndex OBJECT-TYPE
    SYNTAX     Integer32
    MAX-ACCESS not-accessible 
    STATUS     current
    DESCRIPTION
         "Unique index value associated with the Network Port PTP Flow Point."
     ::= { f3PtpNetPortFlowPointEntry 1 }

f3PtpNetPortFlowPointAlias    OBJECT-TYPE
    SYNTAX      DisplayString (SIZE(0..256))
    MAX-ACCESS  read-create
    STATUS      current
    DESCRIPTION
         "This object allows SNMP management entities to provide an 
          alias to the Network Port Flow Point entity."
     ::= { f3PtpNetPortFlowPointEntry 2 }

f3PtpNetPortFlowPointAdminState OBJECT-TYPE
    SYNTAX      AdminState 
    MAX-ACCESS  read-write
    STATUS      current
    DESCRIPTION
            "This object represents the Administrative State of the 
             PTP Flow Point." 
     ::= { f3PtpNetPortFlowPointEntry 3 }

f3PtpNetPortFlowPointOperationalState   OBJECT-TYPE
    SYNTAX      OperationalState 
    MAX-ACCESS  read-only
    STATUS      current
    DESCRIPTION
            "This object represents the Operational State of the PTP Flow 
             Point."
     ::= { f3PtpNetPortFlowPointEntry 4 }

f3PtpNetPortFlowPointSecondaryState     OBJECT-TYPE
    SYNTAX      SecondaryState 
    MAX-ACCESS  read-only
    STATUS      current
    DESCRIPTION
           "This object represents the Secondary State of the PTP Flow Point."
     ::= { f3PtpNetPortFlowPointEntry 5 }

f3PtpNetPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpNetPortFlowPointEntry 6 }

f3PtpNetPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpNetPortFlowPointEntry 7 }

f3PtpNetPortFlowPointService OBJECT-TYPE
    SYNTAX      VariablePointer 
    MAX-ACCESS  read-create
    STATUS      current
    DESCRIPTION
            "This object points to the associated Traffic Service Flow."
    ::= { f3PtpNetPortFlowPointEntry 8 }

f3PtpNetPortFlowPointOuterVlanEtherType OBJECT-TYPE
    SYNTAX      Integer32 
    MAX-ACCESS  read-create
    STATUS      current
    DESCRIPTION
            "This object allows specification of the Outer VLAN Ether Type
             of the PTP Flow."
    ::= { f3PtpNetPortFlowPointEntry 9 }

f3PtpNetPortFlowPointOuterVlanMemberList OBJECT-TYPE
    SYNTAX      DisplayString 
    MAX-ACCESS  read-create
    STATUS      current
    DESCRIPTION
            "This object allows specification of the Outer VLAN(s) 
             of the PTP Flow."
    ::= { f3PtpNetPortFlowPointEntry 10 }

f3PtpNetPortFlowPointOuterUntaggedEnabled OBJECT-TYPE
    SYNTAX      TruthValue 
    MAX-ACCESS  read-create
    STATUS      current
    DESCRIPTION
            "This object allows specification of whether the Outer VLAN
             exists or not." 
    ::= { f3PtpNetPortFlowPointEntry 11 }

f3PtpNetPortFlowPointInner1VlanEtherType OBJECT-TYPE
    SYNTAX      Integer32 
    MAX-ACCESS  read-create
    STATUS      current
    DESCRIPTION
            "This object allows specification of the Inner1 VLAN Ether Type
             of the PTP Flow."
    ::= { f3PtpNetPortFlowPointEntry 12 }

f3PtpNetPortFlowPointInner1VlanMemberList OBJECT-TYPE
    SYNTAX      DisplayString 
    MAX-ACCESS  read-create
    STATUS      current
    DESCRIPTION
            "This object allows specification of the Inner1 VLAN(s) 
             of the PTP Flow."
    ::= { f3PtpNetPortFlowPointEntry 13 }

f3PtpNetPortFlowPointInner1UntaggedEnabled OBJECT-TYPE
    SYNTAX      TruthValue 
    MAX-ACCESS  read-create
    STATUS      current
    DESCRIPTION
            "This object allows specification of whether the Inner1 VLAN
             exists or not." 
    ::= { f3PtpNetPortFlowPointEntry 14 }

f3PtpNetPortFlowPointInner2VlanEtherType OBJECT-TYPE
    SYNTAX      Integer32 
    MAX-ACCESS  read-create
    STATUS      current
    DESCRIPTION
            "This object allows specification of the Inner2 VLAN Ether Type
             of the PTP Flow."
    ::= { f3PtpNetPortFlowPointEntry 15 }

f3PtpNetPortFlowPointInner2VlanMemberList OBJECT-TYPE
    SYNTAX      DisplayString 
    MAX-ACCESS  read-create
    STATUS      current
    DESCRIPTION
            "This object allows specification of the Inner2 VLAN(s) 
             of the PTP Flow."
    ::= { f3PtpNetPortFlowPointEntry 16 }

f3PtpNetPortFlowPointInner2UntaggedEnabled OBJECT-TYPE
    SYNTAX      TruthValue 
    MAX-ACCESS  read-create
    STATUS      current
    DESCRIPTION
            "This object allows specification of whether the Inner1 VLAN
             exists or not." 
    ::= { f3PtpNetPortFlowPointEntry 17 }

f3PtpNetPortFlowPointStorageType OBJECT-TYPE
    SYNTAX     StorageType
    MAX-ACCESS read-create
    STATUS     current
    DESCRIPTION
            "The type of storage configured for this entry."
    ::= { f3PtpNetPortFlowPointEntry 18 }

f3PtpNetPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpNetPortFlowPointRowStatus supported are
            createAndGo(4) and destroy(6).  All mandatory attributes
            must be specified in a single SNMP SET request with
            f3PtpNetPortFlowPointRowStatus value as createAndGo(4).
            Upon successful row creation, this object has a
            value of active(1).

            The f3PtpNetPortFlowPointRowStatus object may be modified if
            the associated instance of this object is equal to active(1)."
    ::= { f3PtpNetPortFlowPointEntry 19 }

f3PtpNetPortFlowPointCOS OBJECT-TYPE
    SYNTAX      Integer32 (0..7)
    MAX-ACCESS  read-create
    STATUS      current
    DESCRIPTION
            "This object allows specification of Class of Service of the PTP traffic
             associated with this Flow Point."
    ::= { f3PtpNetPortFlowPointEntry 20 }

f3PtpNetPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpNetPortFlowPointEntry 21 }

f3PtpNetPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpNetPortFlowPointEntry 22 }

f3PtpNetPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpNetPortFlowPointEntry 23 }

f3PtpNetPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpNetPortFlowPointEntry 24 }

f3PtpNetPortFlowPointBufferSize OBJECT-TYPE
    SYNTAX      Unsigned32
    MAX-ACCESS  read-create
    STATUS      current
    DESCRIPTION
            "This object allows specification the Buffer Size of the queue associated
             with this Flow Point."
    ::= { f3PtpNetPortFlowPointEntry 25 }

f3PtpNetPortFlowPointLoopAvoidance OBJECT-TYPE
    SYNTAX      VariablePointer
    MAX-ACCESS  read-create
    STATUS      current
    DESCRIPTION
            "This object allows specify OID of this associated Loop Avoidance protocol entity."
    ::= { f3PtpNetPortFlowPointEntry 26 }

f3PtpNetPortFlowPointRefConnectGuardFlow OBJECT-TYPE
    SYNTAX      VariablePointer
    MAX-ACCESS  read-write
    STATUS      current
    DESCRIPTION
           "This object specifies Mac Sec flow object OID."
    ::= { f3PtpNetPortFlowPointEntry 27 }

f3PtpNetPortFlowPointSecureState OBJECT-TYPE
    SYNTAX      FlowSecState
    MAX-ACCESS  read-only
    STATUS      current
    DESCRIPTION
           "This object specifies the secure state of this flow."
    ::= { f3PtpNetPortFlowPointEntry 28 }

f3PtpNetPortFlowPointSecureBlockingEnabled OBJECT-TYPE
    SYNTAX      TruthValue
    MAX-ACCESS  read-write
    STATUS      current
    DESCRIPTION
           "This object can be used to enable/disable secure block."
    ::= { f3PtpNetPortFlowPointEntry 29 }






f3PtpEthernetAccPortExtTable  OBJECT-TYPE
    SYNTAX      SEQUENCE OF F3PtpEthernetAccPortExtEntry
    MAX-ACCESS  not-accessible
    STATUS      current
    DESCRIPTION
            "This table extends cmEthernetAccPortTable by adding PTP related parameters."
    ::= { f3PtpConfigObjects 8 }

f3PtpEthernetAccPortExtEntry OBJECT-TYPE
    SYNTAX      F3PtpEthernetAccPortExtEntry
    MAX-ACCESS  not-accessible
    STATUS      current
    DESCRIPTION
            "A conceptual row in the f3PtpEthernetAccPortExtTable."
    AUGMENTS { cmEthernetAccPortEntry }
    ::= { f3PtpEthernetAccPortExtTable 1 }

F3PtpEthernetAccPortExtEntry ::= SEQUENCE {
    f3PtpEthernetAccPortDelayAsymmetry Integer32
}

f3PtpEthernetAccPortDelayAsymmetry OBJECT-TYPE
     SYNTAX     Integer32
     MAX-ACCESS read-write
     STATUS     current
     DESCRIPTION
         "This object allows configuring Delay Asymmetry in nanoseconds on 
          the Ethernet Access Port. The default value is 0."
     ::= { f3PtpEthernetAccPortExtEntry 1 }

f3PtpEthernetNetPortExtTable  OBJECT-TYPE
    SYNTAX      SEQUENCE OF F3PtpEthernetNetPortExtEntry
    MAX-ACCESS  not-accessible
    STATUS      current
    DESCRIPTION
            "This table extends cmEthernetNetPortTable by adding PTP related parameters."
    ::= { f3PtpConfigObjects 9 }

f3PtpEthernetNetPortExtEntry OBJECT-TYPE
    SYNTAX      F3PtpEthernetNetPortExtEntry
    MAX-ACCESS  not-accessible
    STATUS      current
    DESCRIPTION
            "A conceptual row in the f3PtpEthernetNetPortExtTable."
    AUGMENTS { cmEthernetNetPortEntry }
    ::= { f3PtpEthernetNetPortExtTable 1 }

F3PtpEthernetNetPortExtEntry ::= SEQUENCE {
    f3PtpEthernetNetPortDelayAsymmetry Integer32
}

f3PtpEthernetNetPortDelayAsymmetry OBJECT-TYPE
     SYNTAX     Integer32
     MAX-ACCESS read-write
     STATUS     current
     DESCRIPTION
         "This object allows configuring Delay Asymmetry in nanoseconds on 
          the Ethernet Network Port. The default value is 0."
     ::= { f3PtpEthernetNetPortExtEntry 1 }

--
-- Scalars
--
f3PtpConfigScalars             OBJECT IDENTIFIER ::= {f3PtpConfigObjects 10}

f3PtpSysTimeOfDayClock  OBJECT-TYPE
    SYNTAX      VariablePointer
    MAX-ACCESS  read-write
    STATUS      current
    DESCRIPTION
            "This objects allows configuing PTP Telecom Slave object to be used as 
             clock source for System Time of Day. 
             This object is applicable when sysTimeOfDayType object is set to 'ptp' and 
             points to f3PtpTSAlias.
             When sysTimeOfDayType is set to value other than 'ptp' this object should
             return zeroDotZero."
    ::= { f3PtpConfigScalars 1 }


f3PtpBCTable OBJECT-TYPE
    SYNTAX     SEQUENCE OF F3PtpBCEntry
    MAX-ACCESS not-accessible
    STATUS     current
    DESCRIPTION
       "A list of entries corresponding to the PTP Boundary Clock entities."
    ::= { f3PtpConfigObjects 11 }

f3PtpBCEntry OBJECT-TYPE
    SYNTAX     F3PtpBCEntry
    MAX-ACCESS not-accessible
    STATUS     current
    DESCRIPTION
          "An entry containing information applicable to a particular
           Boundary Clock Entity."
    INDEX { neIndex, f3PtpBCIndex}
            
    ::= { f3PtpBCTable 1 }

F3PtpBCEntry ::= SEQUENCE {
    f3PtpBCIndex              Integer32,
    f3PtpBCAlias              DisplayString,
    f3PtpBCAdminState         AdminState,
    f3PtpBCOperationalState   OperationalState,
    f3PtpBCSecondaryState     SecondaryState,
    f3PtpBCClockIdentity      ClockIdentity,
    f3PtpBCTimingSource       VariablePointer,
    f3PtpBCClockClass         Unsigned32,
    f3PtpBCDomainNumber       Integer32,
    f3PtpBCStorageType        StorageType,
    f3PtpBCRowStatus          RowStatus,
    f3PtpBCPhysicalEntityIndex  Integer32,
    f3PtpBCMediationControl     TruthValue
}

f3PtpBCIndex OBJECT-TYPE
    SYNTAX     Integer32
    MAX-ACCESS not-accessible 
    STATUS     current
    DESCRIPTION
         "Unique index value associated with the Boundary Clock Entity."
     ::= { f3PtpBCEntry 1 }

f3PtpBCAlias    OBJECT-TYPE
    SYNTAX      DisplayString (SIZE(0..256))
    MAX-ACCESS  read-create
    STATUS      current
    DESCRIPTION
         "This object allows SNMP management entities to provide an 
          alias to the Boundary Clock entity."
     ::= { f3PtpBCEntry 2 }

f3PtpBCAdminState OBJECT-TYPE
    SYNTAX      AdminState 
    MAX-ACCESS  read-create
    STATUS      current
    DESCRIPTION
          "This object represents the Administrative State of the Boundary Clock."
    ::= { f3PtpBCEntry 3 }

f3PtpBCOperationalState   OBJECT-TYPE
    SYNTAX      OperationalState 
    MAX-ACCESS  read-only
    STATUS      current
    DESCRIPTION
          "This object represents the Operational State of the Boundary Clock." 
    ::= { f3PtpBCEntry 4 }

f3PtpBCSecondaryState     OBJECT-TYPE
    SYNTAX      SecondaryState 
    MAX-ACCESS  read-only
    STATUS      current
    DESCRIPTION
           "This object represents the Secondary State of the Boundary Clock."
    ::= { f3PtpBCEntry 5 }

f3PtpBCClockIdentity OBJECT-TYPE
    SYNTAX     ClockIdentity 
    MAX-ACCESS read-create
    STATUS     current
    DESCRIPTION
         "This object specifies the Clock Identity of the PTP Boundary Clock." 
     ::= { f3PtpBCEntry 6 }

f3PtpBCTimingSource OBJECT-TYPE
    SYNTAX     VariablePointer 
    MAX-ACCESS read-create
    STATUS     current
    DESCRIPTION
         "This object specifies Boundary clock frequency and TOD source EID."
     ::= { f3PtpBCEntry 7 }

f3PtpBCClockClass OBJECT-TYPE
    SYNTAX     Unsigned32 
    MAX-ACCESS read-only
    STATUS     deprecated
    DESCRIPTION
         "This object provides the entry from the f3PtpTSTable, which is
          used as frequency and time of day source this Boundary Clock."
     ::= { f3PtpBCEntry 8 }

f3PtpBCDomainNumber OBJECT-TYPE
    SYNTAX     Integer32 
    MAX-ACCESS read-create
    STATUS     current
    DESCRIPTION
         "This object provides the entry from the f3PtpTSTable, which is
          used as frequency and time of day source this Boundary Clock."
     ::= { f3PtpBCEntry 9 }

f3PtpBCStorageType OBJECT-TYPE
    SYNTAX     StorageType
    MAX-ACCESS read-create
    STATUS     current
    DESCRIPTION
            "The type of storage configured for this entry."
    ::= { f3PtpBCEntry 10 }

f3PtpBCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpBCRowStatus supported are
            createAndGo(4) and destroy(6).  All mandatory attributes
            must be specified in a single SNMP SET request with
            f3PtpBCRowStatus value as createAndGo(4).
            Upon successful row creation, this object has a
            value of active(1).

            The f3PtpBCRowStatus object may be modified if
            the associated instance of this object is equal to active(1)."
    ::= { f3PtpBCEntry 11 }

f3PtpBCPhysicalEntityIndex OBJECT-TYPE
    SYNTAX     Integer32
    MAX-ACCESS read-create
    STATUS     current
    DESCRIPTION
            "Populated with index into the physEntityTable (always point to left card slot in case of protection)"
    ::= { f3PtpBCEntry 12 }

f3PtpBCMediationControl OBJECT-TYPE
    SYNTAX     TruthValue
    MAX-ACCESS read-create
    STATUS     current
    DESCRIPTION
            "Enable/disable BC Mediation Control"
    ::= { f3PtpBCEntry 13 }

--
-- Master Clock Table 
--
f3PtpMasterClockTable OBJECT-TYPE
    SYNTAX     SEQUENCE OF F3PtpMasterClockEntry
    MAX-ACCESS not-accessible
    STATUS     current
    DESCRIPTION
       "A list of entries corresponding to the PTP Master Clock entities."
    ::= { f3PtpConfigObjects 12 }

f3PtpMasterClockEntry OBJECT-TYPE
    SYNTAX     F3PtpMasterClockEntry
    MAX-ACCESS not-accessible
    STATUS     current
    DESCRIPTION
          "An entry containing information applicable to a particular
           Master Clock Entity."
    INDEX { neIndex, f3PtpMasterClockIndex}
            
    ::= { f3PtpMasterClockTable 1 }

F3PtpMasterClockEntry ::= SEQUENCE {
    f3PtpMasterClockIndex              Integer32,
    f3PtpMasterClockAlias              DisplayString,
    f3PtpMasterClockAdminState         AdminState,
    f3PtpMasterClockOperationalState   OperationalState,
    f3PtpMasterClockSecondaryState     SecondaryState,
    f3PtpMasterClockClockIdentity      ClockIdentity,
    f3PtpMasterClockTimeClock          VariablePointer,
    f3PtpMasterClockDomainNumber       Integer32,
    f3PtpMasterClockPriority1          Unsigned32,
    f3PtpMasterClockPriority2          Unsigned32,
    f3PtpMasterClockClockClass         Unsigned32,
    f3PtpMasterClockClockAccuracy      Unsigned32,
    f3PtpMasterClockTimeScale          TimeScale,
    f3PtpMasterClockUtcOffset          Integer32,
    f3PtpMasterClockStorageType        StorageType,
    f3PtpMasterClockRowStatus          RowStatus,
    f3PtpMasterClockActiveTimeRef      VariablePointer,
    f3PtpMasterClockPTPProfile         PTPProfile,
    f3PtpMasterClockPhysicalEntityIndex              Integer32,
    f3PtpMasterClockActiveGrantsAnnounceService      Integer32,
    f3PtpMasterClockActiveGrantsSyncService          Integer32,
    f3PtpMasterClockActiveGrantsDelayRequestService  Integer32,
    f3PtpMasterClockServiceAvailableTime             Unsigned32,
    f3PtpMasterClockServiceUnavailableTime           Unsigned32,
    f3PtpMasterClockServiceAvailablePercentage       DisplayString,
    f3PtpMasterClockSmpteSystemFrameRateNumerator    Unsigned32,
    f3PtpMasterClockSmpteSystemFrameRateDenominator  Unsigned32,
    f3PtpMasterClockSmpteTimeAddressFlags            Integer32

}

f3PtpMasterClockIndex OBJECT-TYPE
    SYNTAX     Integer32
    MAX-ACCESS not-accessible 
    STATUS     current
    DESCRIPTION
         "Unique index value associated with the Boundary Clock Entity."
     ::= { f3PtpMasterClockEntry 1 }

f3PtpMasterClockAlias    OBJECT-TYPE
    SYNTAX      DisplayString (SIZE(0..256))
    MAX-ACCESS  read-create
    STATUS      current
    DESCRIPTION
         "This object allows SNMP management entities to provide an 
          alias to the Master Clock entity."
     ::= { f3PtpMasterClockEntry 2 }

f3PtpMasterClockAdminState OBJECT-TYPE
    SYNTAX      AdminState 
    MAX-ACCESS  read-create
    STATUS      current
    DESCRIPTION
          "This object represents the Administrative State of the Master Clock."
    ::= { f3PtpMasterClockEntry 3 }

f3PtpMasterClockOperationalState   OBJECT-TYPE
    SYNTAX      OperationalState 
    MAX-ACCESS  read-only
    STATUS      current
    DESCRIPTION
          "This object represents the Operational State of the Master Clock." 
    ::= { f3PtpMasterClockEntry 4 }

f3PtpMasterClockSecondaryState     OBJECT-TYPE
    SYNTAX      SecondaryState 
    MAX-ACCESS  read-only
    STATUS      current
    DESCRIPTION
           "This object represents the Secondary State of the Master Clock."
    ::= { f3PtpMasterClockEntry 5 }

f3PtpMasterClockClockIdentity OBJECT-TYPE
    SYNTAX     ClockIdentity 
    MAX-ACCESS read-create
    STATUS     current
    DESCRIPTION
         "This object specifies the Clock Identity of the PTP Boundary Clock." 
     ::= { f3PtpMasterClockEntry 6 }

f3PtpMasterClockTimeClock OBJECT-TYPE
    SYNTAX     VariablePointer 
    MAX-ACCESS read-create
    STATUS     current
    DESCRIPTION
         "This object provides the entry from the f3TimeClockTable, which is
          used as frequency and time of day source this Master Clock."
     ::= { f3PtpMasterClockEntry 7 }

f3PtpMasterClockDomainNumber OBJECT-TYPE
    SYNTAX     Integer32 
    MAX-ACCESS read-create
    STATUS     current
    DESCRIPTION
          "This object allows specification of the PTP domain number of the
           Master Clock ."
     ::= { f3PtpMasterClockEntry 8 }
     
f3PtpMasterClockPriority1 OBJECT-TYPE
    SYNTAX     Unsigned32 (0..255) 
    MAX-ACCESS read-create
    STATUS     current
    DESCRIPTION
         ""
     ::= { f3PtpMasterClockEntry 9 }
     
f3PtpMasterClockPriority2 OBJECT-TYPE
    SYNTAX     Unsigned32 (0..255) 
    MAX-ACCESS read-create
    STATUS     current
    DESCRIPTION
         ""
     ::= { f3PtpMasterClockEntry 10 }

f3PtpMasterClockClockClass OBJECT-TYPE
    SYNTAX     Unsigned32 
    MAX-ACCESS read-only
    STATUS     deprecated
    DESCRIPTION
         "This object provides the Time Clock Clock Class"
     ::= { f3PtpMasterClockEntry 11 }
     
f3PtpMasterClockClockAccuracy OBJECT-TYPE
    SYNTAX     Unsigned32 
    MAX-ACCESS read-only
    STATUS     obsolete
    DESCRIPTION
         "This object indicates Clock accuracy of the clock"
     ::= { f3PtpMasterClockEntry 12 }

f3PtpMasterClockTimeScale   OBJECT-TYPE
    SYNTAX      TimeScale 
    MAX-ACCESS  read-only
    STATUS      current
    DESCRIPTION
          "" 
    ::= { f3PtpMasterClockEntry 13 }

f3PtpMasterClockUtcOffset OBJECT-TYPE
    SYNTAX     Integer32 
    MAX-ACCESS read-only
    STATUS     current
    DESCRIPTION
          "Seconds offset between TAI and UTC"
     ::= { f3PtpMasterClockEntry 14 }
     
     
f3PtpMasterClockStorageType OBJECT-TYPE
    SYNTAX     StorageType
    MAX-ACCESS read-create
    STATUS     current
    DESCRIPTION
            "The type of storage configured for this entry."
    ::= { f3PtpMasterClockEntry 15 }

f3PtpMasterClockRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMasterClockRowStatus supported are
            createAndGo(4) and destroy(6).  All mandatory attributes
            must be specified in a single SNMP SET request with
            f3PtpMasterClockRowStatus value as createAndGo(4).
            Upon successful row creation, this object has a
            value of active(1).

            The f3PtpMasterClockRowStatus object may be modified if
            the associated instance of this object is equal to active(1)."
    ::= { f3PtpMasterClockEntry 16 }

f3PtpMasterClockActiveTimeRef OBJECT-TYPE
    SYNTAX     VariablePointer 
    MAX-ACCESS read-only
    STATUS     current
    DESCRIPTION
         "This object specifies timig reference of the Master Clock."
     ::= { f3PtpMasterClockEntry 17 }

f3PtpMasterClockPTPProfile OBJECT-TYPE
    SYNTAX     PTPProfile
    MAX-ACCESS read-create
    STATUS     current
    DESCRIPTION
            "This object describe the Master Clock PTP Profile."
    ::= { f3PtpMasterClockEntry 18 }

f3PtpMasterClockPhysicalEntityIndex OBJECT-TYPE
    SYNTAX     Integer32
    MAX-ACCESS read-create
    STATUS     current
    DESCRIPTION
            "Populated with index into the physEntityTable (always point to left card slot in case of protection)"
    ::= { f3PtpMasterClockEntry 19 }


f3PtpMasterClockActiveGrantsAnnounceService OBJECT-TYPE
    SYNTAX     Integer32
    MAX-ACCESS read-only
    STATUS     current
    DESCRIPTION
            "Report number of active grants announce service."
    ::= { f3PtpMasterClockEntry 20 }

f3PtpMasterClockActiveGrantsSyncService OBJECT-TYPE
    SYNTAX     Integer32
    MAX-ACCESS read-only
    STATUS     current
    DESCRIPTION
            "Report number of active grants sync service."
    ::= { f3PtpMasterClockEntry 21 }

f3PtpMasterClockActiveGrantsDelayRequestService OBJECT-TYPE
    SYNTAX     Integer32
    MAX-ACCESS read-only
    STATUS     current
    DESCRIPTION
            "Report number of active grants delay-request service."
    ::= { f3PtpMasterClockEntry 22 }

f3PtpMasterClockServiceAvailableTime OBJECT-TYPE
    SYNTAX     Unsigned32
    MAX-ACCESS read-only
    STATUS     current
    DESCRIPTION
            "This object allows to manage service available time (seconds) for PTP."
    ::= { f3PtpMasterClockEntry 23 }

f3PtpMasterClockServiceUnavailableTime OBJECT-TYPE
    SYNTAX     Unsigned32
    MAX-ACCESS read-only
    STATUS     current
    DESCRIPTION
            "This object allows to manage service unavailable  time (seconds) for PTP."
    ::= { f3PtpMasterClockEntry 24 }

f3PtpMasterClockServiceAvailablePercentage OBJECT-TYPE
    SYNTAX     DisplayString
    MAX-ACCESS read-only
    STATUS     current
    DESCRIPTION
            "This object allows to manage service available in percentage [XXX.YY%] for PTP."
    ::= { f3PtpMasterClockEntry 25 }

f3PtpMasterClockSmpteSystemFrameRateNumerator OBJECT-TYPE
    SYNTAX     Unsigned32
    MAX-ACCESS read-write
    STATUS     current
    DESCRIPTION
            "This object allows to manage the frame rate (Numerator) for PTP Broadcast Profile."
    ::= { f3PtpMasterClockEntry 26 }

f3PtpMasterClockSmpteSystemFrameRateDenominator OBJECT-TYPE
    SYNTAX     Unsigned32
    MAX-ACCESS read-write
    STATUS     current
    DESCRIPTION
            "This object allows to manage the frame rate (Denominator) for PTP Broadcast Profile."
    ::= { f3PtpMasterClockEntry 27 }

f3PtpMasterClockSmpteTimeAddressFlags OBJECT-TYPE
    SYNTAX     Integer32 (0..255) 
    MAX-ACCESS read-write
    STATUS     current
    DESCRIPTION
            "This object allows to manage the flags for PTP Broadcast Profile."
    ::= { f3PtpMasterClockEntry 28 }

--
-- Master Clock Interface Table 
--
f3PtpMCITable OBJECT-TYPE
    SYNTAX     SEQUENCE OF F3PtpMCIEntry
    MAX-ACCESS not-accessible
    STATUS     current
    DESCRIPTION
       "A list of entries corresponding to the PTP Master Clock Interface entities."
    ::= { f3PtpConfigObjects 13 }

f3PtpMCIEntry OBJECT-TYPE
    SYNTAX     F3PtpMCIEntry
    MAX-ACCESS not-accessible
    STATUS     current
    DESCRIPTION
          "An entry containing information applicable to a particular
           Master Clock Interface Entity."
    INDEX { neIndex, f3PtpBCIndex, f3PtpMCIIndex }
    ::= { f3PtpMCITable 1 }

F3PtpMCIEntry ::= SEQUENCE {
    f3PtpMCIIndex                       Integer32,
    f3PtpMCIAlias                       DisplayString,
    f3PtpMCIAdminState                  AdminState,
    f3PtpMCIOperationalState            OperationalState,
    f3PtpMCISecondaryState              SecondaryState,
    f3PtpMCIPortIdentity                PortIdentity,
    f3PtpMCIDomainNumber                Integer32,
    f3PtpMCIClockType                   MasterClockType,
    f3PtpMCIDelayMechanism              DelayMechanism,
    f3PtpMCIIfName                      DisplayString,
    f3PtpMCIIpProtocol                  IpVersion,
    f3PtpMCIMasterIpV4Address           IpAddress,
    f3PtpMCIMasterIpV4SubnetMask        IpAddress,
    f3PtpMCIIpPriorityMapMode           IpPriorityMapMode,
    f3PtpMCIIpPriority                  Integer32,
    f3PtpMCIMaxLeaseDuration            Integer32,
    f3PtpMCIMaxSlavesSupported          Integer32,
    f3PtpMCIMaxStaticSlavesSupported    Integer32,
    f3PtpMCIMaxSyncMsgRate              SyncMsgRate,
    f3PtpMCIMaxDelayRespMsgRate         DelayRespMsgRate,
    f3PtpMCIMaxAnnounceMsgRate          AnnounceMsgRate,
    f3PtpMCIStorageType                 StorageType,
    f3PtpMCIRowStatus                   RowStatus,
    f3PtpMCIServiceFlow                 VariablePointer,
    f3PtpMCIClockClassProfile           ClockClassProfile,
    f3PtpMCIClockClass                  Unsigned32,
    f3PtpMCIAnnounceExtTLVEnable        TruthValue,
    f3PtpMCIPtpTransport                PTPTransport,
    f3PtpMCIPtpTransportMode            PTPTransportMode,
    f3PtpMCIPtpRemoteSlaveAgingTimeout  Integer32,
    f3PtpMCIMasterIpV6Address           Ipv6Address,             
    f3PtpMCIMasterIpV6AddrPrefixLength  Integer32,

    f3PtpMCIDefaultGatewayControl       ToggleValue,
    f3PtpMCIGateway                     IpAddress,
    f3PtpMCIIpV6Gateway                 Ipv6Address,
    f3PtpMCISlavesWarningThreshold      SlavesPercentage,
    
    f3PtpMCIForcePRTCClockQuality       ToggleValue
}

f3PtpMCIIndex OBJECT-TYPE
    SYNTAX     Integer32
    MAX-ACCESS not-accessible 
    STATUS     current
    DESCRIPTION
         "Unique index value associated with the Master Clock Interface."
     ::= { f3PtpMCIEntry 1 }

f3PtpMCIAlias    OBJECT-TYPE
    SYNTAX      DisplayString (SIZE(0..256))
    MAX-ACCESS  read-create
    STATUS      current
    DESCRIPTION
         "This object allows SNMP management entities to provide an 
          alias to the Master Clock Interface entity."
     ::= { f3PtpMCIEntry 2 }

f3PtpMCIAdminState OBJECT-TYPE
    SYNTAX      AdminState 
    MAX-ACCESS  read-create
    STATUS      current
    DESCRIPTION
          "This object represents the Administrative State of the Master Clock Interface."
    ::= { f3PtpMCIEntry 3 }

f3PtpMCIOperationalState   OBJECT-TYPE
    SYNTAX      OperationalState 
    MAX-ACCESS  read-only
    STATUS      current
    DESCRIPTION
          "This object represents the Operational State of the Master Clock Interface." 
    ::= { f3PtpMCIEntry 4 }

f3PtpMCISecondaryState     OBJECT-TYPE
    SYNTAX      SecondaryState 
    MAX-ACCESS  read-only
    STATUS      current
    DESCRIPTION
           "This object represents the Secondary State of the Master Clock Interface."
    ::= { f3PtpMCIEntry 5 }

f3PtpMCIPortIdentity OBJECT-TYPE
    SYNTAX     PortIdentity 
    MAX-ACCESS read-only
    STATUS     current
    DESCRIPTION
         "This object represents the PTP Port Identity of the Master Clock Interface." 
     ::= { f3PtpMCIEntry 6 }

f3PtpMCIDomainNumber OBJECT-TYPE
    SYNTAX     Integer32 
    MAX-ACCESS read-write
    STATUS     current
    DESCRIPTION
         "This object allows specification of the PTP domain number of the
           Master Clock Interface." 
     ::= { f3PtpMCIEntry 7 }

f3PtpMCIClockType OBJECT-TYPE
    SYNTAX     MasterClockType
    MAX-ACCESS read-create 
    STATUS     current
    DESCRIPTION
         "This object must be used to specify the type of the Master Clock Interface."
     ::= { f3PtpMCIEntry 8 }

f3PtpMCIDelayMechanism OBJECT-TYPE
    SYNTAX      DelayMechanism 
    MAX-ACCESS  read-create
    STATUS      current
    DESCRIPTION
            "This object  represents the Delay Mechanism of the  Master Clock Interface."
    ::= { f3PtpMCIEntry 9 }

f3PtpMCIIfName     OBJECT-TYPE
    SYNTAX         DisplayString (SIZE(1..15))
    MAX-ACCESS     read-create
    STATUS         current
    DESCRIPTION
         "This object allows SNMP management entities to provide a
          name to the Slave Only Ordinary Clock.  This is used
          for creation of the underlying IP Interface associated 
          with the Master Clock Interface."
     ::= { f3PtpMCIEntry 10 }

f3PtpMCIIpProtocol OBJECT-TYPE
    SYNTAX     IpVersion
    MAX-ACCESS read-create 
    STATUS     current
    DESCRIPTION
         "This object allows specification of the IP Protocol to
          communicate with Remote Slaves. Only ipv4 is supported."
     ::= { f3PtpMCIEntry 11 }

f3PtpMCIMasterIpV4Address OBJECT-TYPE
    SYNTAX     IpAddress
    MAX-ACCESS read-create 
    STATUS     current
    DESCRIPTION
         "This object allows specification of the IPv4 Address of
          the PTP Master."
     ::= { f3PtpMCIEntry 12 }

f3PtpMCIMasterIpV4SubnetMask OBJECT-TYPE
    SYNTAX     IpAddress
    MAX-ACCESS read-create 
    STATUS     current
    DESCRIPTION
         "This object allows specification of the IPv4 Subnet Mask of
          the PTP Master."
     ::= { f3PtpMCIEntry 13 }

f3PtpMCIIpPriorityMapMode  OBJECT-TYPE
    SYNTAX     IpPriorityMapMode 
    MAX-ACCESS read-create
    STATUS     current
    DESCRIPTION
         "This object enables specification of Priority Mapping Mode for
          the  Master Clock Interface."
     ::= { f3PtpMCIEntry 14 }

f3PtpMCIIpPriority  OBJECT-TYPE
    SYNTAX     Integer32 (0..63)
    MAX-ACCESS read-create
    STATUS     current
    DESCRIPTION
         "This object enables specification of Priority Value for
          f3PtpMCIIpPriorityMapMode as priomap-tos,priomap-dscp."
     ::= { f3PtpMCIEntry 15 }

f3PtpMCIMaxLeaseDuration  OBJECT-TYPE
    SYNTAX     Integer32
    MAX-ACCESS read-create
    STATUS     current
    DESCRIPTION
         "This enables specification of maximum lease duration for granted announce, 
          Sync and Delay Response service in seconds."
     ::= { f3PtpMCIEntry 16 }

f3PtpMCIMaxSlavesSupported OBJECT-TYPE
    SYNTAX     Integer32
    MAX-ACCESS read-write
    STATUS     current
    DESCRIPTION
         "This attribute specifies maximum total number of Static and Dynamic
          Remote Slaves supported by the Master Clock Interface."
     ::= { f3PtpMCIEntry 17 }

f3PtpMCIMaxStaticSlavesSupported OBJECT-TYPE
    SYNTAX     Integer32
    MAX-ACCESS read-write
    STATUS     current
    DESCRIPTION
         "This attribute specifies maximum  total number of Static
          Remote Slaves supported by the Master Clock Interface."
     ::= { f3PtpMCIEntry 18 }

f3PtpMCIMaxSyncMsgRate OBJECT-TYPE
    SYNTAX     SyncMsgRate
    MAX-ACCESS read-create
    STATUS     current
    DESCRIPTION
         "This attribute specifies maximum allowed negotiated Sync Messages rate per 
          remote Slave Clock with UMN enabled of default Sync Messages rate per 
          remote Slave Clock with UMN disabled."
     ::= { f3PtpMCIEntry 19 }

f3PtpMCIMaxDelayRespMsgRate OBJECT-TYPE
    SYNTAX     DelayRespMsgRate
    MAX-ACCESS read-create
    STATUS     current
    DESCRIPTION
         "This attribute specifies maximum allowed negotiated Delay_Resp Messages rate 
          per remote Slave Clock with UMN enabled of default Delay_Resp Messages rate 
          per remote Slave Clock with UMN disabled."
     ::= { f3PtpMCIEntry 20 }

f3PtpMCIMaxAnnounceMsgRate OBJECT-TYPE
    SYNTAX     AnnounceMsgRate
    MAX-ACCESS read-create
    STATUS     current
    DESCRIPTION
         "This attribute specifies maximum allowed negotiated Delay_Req Messages rate 
          per remote Slave Clock with UMN enabled of default Delay_Req Messages rate 
          per remote Slave Clock with UMN disabled."
     ::= { f3PtpMCIEntry 21 }

f3PtpMCIStorageType OBJECT-TYPE
    SYNTAX     StorageType
    MAX-ACCESS read-create
    STATUS     current
    DESCRIPTION
            "The type of storage configured for this entry."
    ::= { f3PtpMCIEntry 22 }

f3PtpMCIRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMCIRowStatus supported are
            createAndGo(4) and destroy(6).  All mandatory attributes
            must be specified in a single SNMP SET request with
            f3PtpMCIRowStatus value as createAndGo(4).
            Upon successful row creation, this object has a
            value of active(1).

            The f3PtpMCIRowStatus object may be modified if
            the associated instance of this object is equal to active(1)."
    ::= { f3PtpMCIEntry 23 }

f3PtpMCIServiceFlow OBJECT-TYPE
    SYNTAX     VariablePointer
    MAX-ACCESS read-write
    STATUS     current
    DESCRIPTION
            "This object describe the associated service flow."
    ::= { f3PtpMCIEntry 24 }


f3PtpMCIClockClassProfile OBJECT-TYPE
    SYNTAX     ClockClassProfile
    MAX-ACCESS read-create
    STATUS     current
    DESCRIPTION
            "This object describe the Clock Class Profile."
    ::= { f3PtpMCIEntry 25 }

f3PtpMCIClockClass OBJECT-TYPE
    SYNTAX     Unsigned32 
    MAX-ACCESS read-only
    STATUS     current
    DESCRIPTION
         "This object provides the MCI Clock Class"
     ::= { f3PtpMCIEntry 26 }

f3PtpMCIAnnounceExtTLVEnable OBJECT-TYPE
    SYNTAX     TruthValue
    MAX-ACCESS read-create
    STATUS     current
    DESCRIPTION
         "This object determines whether the announce message has a TLV extension"
     ::= { f3PtpMCIEntry 27 }


f3PtpMCIPtpTransport OBJECT-TYPE
    SYNTAX     PTPTransport
    MAX-ACCESS read-create
    STATUS     current
    DESCRIPTION
         "This object specifies the PTP transport"
     ::= { f3PtpMCIEntry 28 }

f3PtpMCIPtpTransportMode OBJECT-TYPE
    SYNTAX     PTPTransportMode
    MAX-ACCESS read-only
    STATUS     current
    DESCRIPTION
         "This object specifies the PTP transport mode"
     ::= { f3PtpMCIEntry 29 }

f3PtpMCIPtpRemoteSlaveAgingTimeout OBJECT-TYPE
    SYNTAX     Integer32 (0..300)
    MAX-ACCESS read-create
    STATUS     current
    DESCRIPTION
         "This attribute (in seconds) specifies the aging timeout for inactive dynamic remote slaves.
          The value 0 means it is never aged.
          Note that this attribute is not applicable to static slaves." 
    DEFVAL { 60 }
     ::= { f3PtpMCIEntry 30 }

f3PtpMCIMasterIpV6Address OBJECT-TYPE
    SYNTAX     Ipv6Address 
    MAX-ACCESS read-create
    STATUS   current
    DESCRIPTION
         "This object allows specification of the unicast ipv6 Address of
          the PTP Master."
    ::= { f3PtpMCIEntry 31 }

f3PtpMCIMasterIpV6AddrPrefixLength OBJECT-TYPE
    SYNTAX     Integer32 (0..128)
    MAX-ACCESS read-create
    STATUS   current
    DESCRIPTION
         "This object allows specification of the unicast IPv6 address prefix length of
          the PTP Master."
    ::= { f3PtpMCIEntry 32 }


f3PtpMCIDefaultGatewayControl OBJECT-TYPE
    SYNTAX     ToggleValue
    MAX-ACCESS read-create
    STATUS     current
    DESCRIPTION
         "This attribute control Gatwaye address for PTP Master."
     ::= { f3PtpMCIEntry 33 }

f3PtpMCIGateway OBJECT-TYPE
    SYNTAX     IpAddress
    MAX-ACCESS read-create 
    STATUS     current
    DESCRIPTION
         "This object allows specification of the IPv4 Gateway Address of
          the PTP Master."
     ::= { f3PtpMCIEntry 34 }

f3PtpMCIIpV6Gateway OBJECT-TYPE
    SYNTAX     Ipv6Address 
    MAX-ACCESS read-create
    STATUS   current
    DESCRIPTION
         "This object allows specification of the IPv6 Gateway Address of
          the PTP Master."
    ::= { f3PtpMCIEntry 35 }

f3PtpMCISlavesWarningThreshold OBJECT-TYPE
    SYNTAX     SlavesPercentage
    MAX-ACCESS read-create
    STATUS     current
    DESCRIPTION
         "This object allows specification of the Slaves Threshold for warning
          with an alarm that a certain percentage of slaves capacity has been crossed.
          The alarm is cleared when the number of remote slaves is back with k slaves
          under the threshold. If the threshold is strictly greater than 11, the value
          of k is 10, and it equals 2 otherwise."
     ::= { f3PtpMCIEntry 36 }
     
 f3PtpMCIForcePRTCClockQuality OBJECT-TYPE                    
    SYNTAX      ToggleValue
    MAX-ACCESS  read-write
    STATUS      current
    DESCRIPTION
           "This object indicate is used to force PRTC attributes when time clock 
           is configured to EPRTC mode."
    ::= { f3PtpMCIEntry 37 }



f3PtpMasterVirtualPortTable OBJECT-TYPE
    SYNTAX     SEQUENCE OF F3PtpMasterVirtualPortEntry
    MAX-ACCESS not-accessible
    STATUS     current
    DESCRIPTION
       "A list of entries corresponding to the PTP Master Clock Interface 
        Virtual Port entities."
    ::= { f3PtpConfigObjects 14 }


f3PtpMasterVirtualPortEntry OBJECT-TYPE
    SYNTAX     F3PtpMasterVirtualPortEntry
    MAX-ACCESS not-accessible
    STATUS     current
    DESCRIPTION
          "An entry containing information applicable to a particular
           Master Clock Interface Virtual Port entity."
    INDEX { neIndex, f3PtpBCIndex, f3PtpMCIIndex, f3PtpMasterVirtualPortIndex}
            
    ::= { f3PtpMasterVirtualPortTable 1 }

F3PtpMasterVirtualPortEntry ::= SEQUENCE {
    f3PtpMasterVirtualPortIndex                    Integer32,
    f3PtpMasterVirtualPortAlias                    DisplayString,
    f3PtpMasterVirtualPortAdminState               AdminState,
    f3PtpMasterVirtualPortOperationalState         OperationalState,
    f3PtpMasterVirtualPortSecondaryState           SecondaryState,
    f3PtpMasterVirtualPortFlowPoint                VariablePointer,
    f3PtpMasterVirtualPortStorageType              StorageType,
    f3PtpMasterVirtualPortRowStatus                RowStatus
}

f3PtpMasterVirtualPortIndex OBJECT-TYPE
    SYNTAX     Integer32
    MAX-ACCESS not-accessible 
    STATUS     current
    DESCRIPTION
         "Unique index value associated with the Master Virtual Port entity."
     ::= { f3PtpMasterVirtualPortEntry 1 }

f3PtpMasterVirtualPortAlias    OBJECT-TYPE
    SYNTAX      DisplayString (SIZE(0..256))
    MAX-ACCESS  read-create
    STATUS      current
    DESCRIPTION
         "This object allows SNMP management entities to provide an 
          alias to the Master Virtual Port entity."
     ::= { f3PtpMasterVirtualPortEntry 2 }

f3PtpMasterVirtualPortAdminState OBJECT-TYPE
    SYNTAX      AdminState 
    MAX-ACCESS  read-create
    STATUS      current
    DESCRIPTION
          "This object represents the Administrative State of the Master Virtual Port."
    ::= { f3PtpMasterVirtualPortEntry 3 }

f3PtpMasterVirtualPortOperationalState   OBJECT-TYPE
    SYNTAX      OperationalState 
    MAX-ACCESS  read-only
    STATUS      current
    DESCRIPTION
          "This object represents the Operational State of the Master Virtual Port."
    ::= { f3PtpMasterVirtualPortEntry 4 }

f3PtpMasterVirtualPortSecondaryState     OBJECT-TYPE
    SYNTAX      SecondaryState 
    MAX-ACCESS  read-only
    STATUS      current
    DESCRIPTION
           "This object represents the Secondary State of the Master Virtual Port."
    ::= { f3PtpMasterVirtualPortEntry 5 }

f3PtpMasterVirtualPortFlowPoint     OBJECT-TYPE
    SYNTAX      VariablePointer 
    MAX-ACCESS  read-create
    STATUS      current
    DESCRIPTION
         "This object associates the PTP Flow Point with the Master Virtual Port."
    ::= { f3PtpMasterVirtualPortEntry 6 }

f3PtpMasterVirtualPortStorageType OBJECT-TYPE
    SYNTAX     StorageType
    MAX-ACCESS read-create
    STATUS     current
    DESCRIPTION
            "The type of storage configured for this entry."
    ::= { f3PtpMasterVirtualPortEntry 7 }

f3PtpMasterVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMasterVirtualPortRowStatus supported are
            createAndGo(4) and destroy(6).  All mandatory attributes
            must be specified in a single SNMP SET request with
            f3PtpMasterVirtualPortRowStatus value as createAndGo(4).
            Upon successful row creation, this object has a
            value of active(1).

            The f3PtpMasterVirtualPortRowStatus object may be modified if
            the associated instance of this object is equal to active(1)."
    ::= { f3PtpMasterVirtualPortEntry 8 }

f3PtpStaticRemoteSlaveTable OBJECT-TYPE
    SYNTAX     SEQUENCE OF F3PtpStaticRemoteSlaveEntry
    MAX-ACCESS not-accessible
    STATUS     current
    DESCRIPTION
       "A list of entries corresponding to the PTP Remote Slave entities."
    ::= { f3PtpConfigObjects 15 }


f3PtpStaticRemoteSlaveEntry OBJECT-TYPE
    SYNTAX     F3PtpStaticRemoteSlaveEntry
    MAX-ACCESS not-accessible
    STATUS     current
    DESCRIPTION
          "An entry containing information applicable to a particular
           Static Remote Slave entity."
    INDEX { neIndex, f3PtpBCIndex, f3PtpMCIIndex, f3PtpStaticRemoteSlaveIndex}
            
    ::= { f3PtpStaticRemoteSlaveTable 1 }

F3PtpStaticRemoteSlaveEntry ::= SEQUENCE {
    f3PtpStaticRemoteSlaveIndex                    Integer32,
    f3PtpStaticRemoteSlaveAlias                    DisplayString,
    f3PtpStaticRemoteSlaveAdminState               AdminState,
    f3PtpStaticRemoteSlaveOperationalState         OperationalState,
    f3PtpStaticRemoteSlaveSecondaryState           SecondaryState,
    f3PtpStaticRemoteSlaveClockIdentity            ClockIdentity,
    f3PtpStaticRemoteSlaveIpV4Address              IpAddress,
    f3PtpStaticRemoteSlaveTimeCreated              DateAndTime,
    f3PtpStaticRemoteSlaveSyncMsgRate              SyncMsgRate,
    f3PtpStaticRemoteSlaveDelayRspMsgRate          DelayRespMsgRate,
    f3PtpStaticRemoteSlaveAnnounceMsgRate          AnnounceMsgRate,
    f3PtpStaticRemoteSlaveNegSyncLeaseDur          Integer32,
    f3PtpStaticRemoteSlaveNegDelayRspLeaseDur      Integer32,
    f3PtpStaticRemoteSlaveNegAnnounceLeaseDur      Integer32,
    f3PtpStaticRemoteSlaveSyncDurRemTime           Unsigned32,
    f3PtpStaticRemoteSlaveDelayRspDurRemTime       Unsigned32,
    f3PtpStaticRemoteSlaveAnnounceDurRemTime       Unsigned32,
    f3PtpStaticRemoteSlaveUmnControl               TruthValue,
    f3PtpStaticRemoteSlaveStorageType              StorageType,
    f3PtpStaticRemoteSlaveRowStatus                RowStatus,
    f3PtpStaticRemoteSlaveIpV6Address              Ipv6Address             

}

f3PtpStaticRemoteSlaveIndex OBJECT-TYPE
    SYNTAX     Integer32
    MAX-ACCESS not-accessible 
    STATUS     current
    DESCRIPTION
         "Unique index value associated with the Remote Slave."
     ::= { f3PtpStaticRemoteSlaveEntry 1 }

f3PtpStaticRemoteSlaveAlias    OBJECT-TYPE
    SYNTAX      DisplayString (SIZE(0..256))
    MAX-ACCESS  read-create
    STATUS      current
    DESCRIPTION
         "This object allows SNMP management entities to provide an 
          alias to the Remote Slave."
     ::= { f3PtpStaticRemoteSlaveEntry 2 }

f3PtpStaticRemoteSlaveAdminState OBJECT-TYPE
    SYNTAX      AdminState 
    MAX-ACCESS  read-create
    STATUS      current
    DESCRIPTION
          "This object represents the Administrative State of the Remote Slave."
    ::= { f3PtpStaticRemoteSlaveEntry 3 }

f3PtpStaticRemoteSlaveOperationalState   OBJECT-TYPE
    SYNTAX      OperationalState 
    MAX-ACCESS  read-only
    STATUS      current
    DESCRIPTION
          "This object represents the Operational State of the Remote Slave."
    ::= { f3PtpStaticRemoteSlaveEntry 4 }

f3PtpStaticRemoteSlaveSecondaryState     OBJECT-TYPE
    SYNTAX      SecondaryState 
    MAX-ACCESS  read-only
    STATUS      current
    DESCRIPTION
           "This object represents the Secondary State of the Remote Slave."
    ::= { f3PtpStaticRemoteSlaveEntry 5 }

f3PtpStaticRemoteSlaveClockIdentity OBJECT-TYPE
    SYNTAX     ClockIdentity 
    MAX-ACCESS read-only
    STATUS     current
    DESCRIPTION
         "This object represents the Clock Identity of the Remote Slave."
     ::= { f3PtpStaticRemoteSlaveEntry 6 }

f3PtpStaticRemoteSlaveIpV4Address OBJECT-TYPE
    SYNTAX     IpAddress
    MAX-ACCESS read-create 
    STATUS     current
    DESCRIPTION
         "This object allows specification of the IPv4 Address of
          the Remote Slave."
     ::= { f3PtpStaticRemoteSlaveEntry 7 }

f3PtpStaticRemoteSlaveTimeCreated OBJECT-TYPE
    SYNTAX     DateAndTime
    MAX-ACCESS read-only 
    STATUS     current
    DESCRIPTION
         "This object presents time when this Remote Slave entity was created."
     ::= { f3PtpStaticRemoteSlaveEntry 8 }

f3PtpStaticRemoteSlaveSyncMsgRate OBJECT-TYPE
    SYNTAX     SyncMsgRate
    MAX-ACCESS read-create
    STATUS     current
    DESCRIPTION
         "This attribute specifies Sync Message Rate of the Remote Slave."
     ::= { f3PtpStaticRemoteSlaveEntry 9 }

f3PtpStaticRemoteSlaveDelayRspMsgRate OBJECT-TYPE
    SYNTAX     DelayRespMsgRate
    MAX-ACCESS read-create
    STATUS     current
    DESCRIPTION
         "This attribute specifies Delay Respone Message Rate of the Remote Slave."
     ::= { f3PtpStaticRemoteSlaveEntry 10 }

f3PtpStaticRemoteSlaveAnnounceMsgRate OBJECT-TYPE
    SYNTAX     AnnounceMsgRate
    MAX-ACCESS read-create
    STATUS     current
    DESCRIPTION
         "This attribute specifies Announce Message Rate of the Remote Slave."
     ::= { f3PtpStaticRemoteSlaveEntry 11 }

f3PtpStaticRemoteSlaveNegSyncLeaseDur OBJECT-TYPE
    SYNTAX     Integer32
    MAX-ACCESS read-only
    STATUS     current
    DESCRIPTION
         "This attribute indicates Sync messages negotiated Lease Duration in seconds."
     ::= { f3PtpStaticRemoteSlaveEntry 12 }

f3PtpStaticRemoteSlaveNegDelayRspLeaseDur OBJECT-TYPE
    SYNTAX     Integer32
    MAX-ACCESS read-only
    STATUS     current
    DESCRIPTION
         "This attribute indicates Delay Response messages negotiated Lease 
          Duration in seconds."
     ::= { f3PtpStaticRemoteSlaveEntry 13 }

f3PtpStaticRemoteSlaveNegAnnounceLeaseDur OBJECT-TYPE
    SYNTAX     Integer32
    MAX-ACCESS read-only
    STATUS     current
    DESCRIPTION
         "This attribute indicates Announce messages negotiated Lease 
          Duration in seconds."
     ::= { f3PtpStaticRemoteSlaveEntry 14 }

f3PtpStaticRemoteSlaveSyncDurRemTime OBJECT-TYPE
    SYNTAX     Unsigned32
    MAX-ACCESS read-only
    STATUS     current
    DESCRIPTION
         "This attribute indicates Remaining seconds of Lease Duration of Sync service."
     ::= { f3PtpStaticRemoteSlaveEntry 15 }

f3PtpStaticRemoteSlaveDelayRspDurRemTime OBJECT-TYPE
    SYNTAX     Unsigned32
    MAX-ACCESS read-only
    STATUS     current
    DESCRIPTION
         "This attribute indicates Remaining seconds of Lease Duration of Delay Response 
          service."
     ::= { f3PtpStaticRemoteSlaveEntry 16 }

f3PtpStaticRemoteSlaveAnnounceDurRemTime OBJECT-TYPE
    SYNTAX     Unsigned32
    MAX-ACCESS read-only
    STATUS     current
    DESCRIPTION
         "This attribute indicates Remaining seconds of Lease Duration of Announce 
          service."
     ::= { f3PtpStaticRemoteSlaveEntry 17 }

f3PtpStaticRemoteSlaveUmnControl OBJECT-TYPE
    SYNTAX     TruthValue
    MAX-ACCESS read-create
    STATUS     current
    DESCRIPTION
         "This attribute controls UMN for the static remote slave."
     ::= { f3PtpStaticRemoteSlaveEntry 18 }

f3PtpStaticRemoteSlaveStorageType OBJECT-TYPE
    SYNTAX     StorageType
    MAX-ACCESS read-create
    STATUS     current
    DESCRIPTION
            "The type of storage configured for this entry."
    ::= { f3PtpStaticRemoteSlaveEntry 19 }

f3PtpStaticRemoteSlaveRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpStaticRemoteSlaveRowStatus supported are
            createAndGo(4) and destroy(6).  All mandatory attributes
            must be specified in a single SNMP SET request with
            f3PtpStaticRemoteSlaveRowStatus value as createAndGo(4).
            Upon successful row creation, this object has a
            value of active(1).

            The f3PtpStaticRemoteSlaveRowStatus object may be modified if
            the associated instance of this object is equal to active(1)."
    ::= { f3PtpStaticRemoteSlaveEntry 20 }


f3PtpStaticRemoteSlaveIpV6Address OBJECT-TYPE
    SYNTAX     Ipv6Address 
    MAX-ACCESS read-create
    STATUS   current
    DESCRIPTION
         "This object allows specification of the unicast IPv6 Address of
          the Remote Slave."
    ::= { f3PtpStaticRemoteSlaveEntry 21 }



f3PtpDynamicRemoteSlaveTable OBJECT-TYPE
    SYNTAX     SEQUENCE OF F3PtpDynamicRemoteSlaveEntry
    MAX-ACCESS not-accessible
    STATUS     current
    DESCRIPTION
       "A list of entries corresponding to the PTP Remote Slave entities."
    ::= { f3PtpConfigObjects 16 }


f3PtpDynamicRemoteSlaveEntry OBJECT-TYPE
    SYNTAX     F3PtpDynamicRemoteSlaveEntry
    MAX-ACCESS not-accessible
    STATUS     current
    DESCRIPTION
          "An entry containing information applicable to a particular
           Dynamic Remote Slave entity."
    INDEX { neIndex, f3PtpBCIndex, f3PtpMCIIndex, f3PtpDynamicRemoteSlaveIndex}
            
    ::= { f3PtpDynamicRemoteSlaveTable 1 }

F3PtpDynamicRemoteSlaveEntry ::= SEQUENCE {
    f3PtpDynamicRemoteSlaveIndex                    Integer32,
    f3PtpDynamicRemoteSlaveAlias                    DisplayString,
    f3PtpDynamicRemoteSlaveAdminState               AdminState,
    f3PtpDynamicRemoteSlaveOperationalState         OperationalState,
    f3PtpDynamicRemoteSlaveSecondaryState           SecondaryState,
    f3PtpDynamicRemoteSlaveClockIdentity            ClockIdentity,
    f3PtpDynamicRemoteSlaveIpV4Address              IpAddress,
    f3PtpDynamicRemoteSlaveTimeCreated              DateAndTime,
    f3PtpDynamicRemoteSlaveSyncMsgRate              SyncMsgRate,
    f3PtpDynamicRemoteSlaveDelayRspMsgRate          DelayRespMsgRate,
    f3PtpDynamicRemoteSlaveAnnounceMsgRate          AnnounceMsgRate,
    f3PtpDynamicRemoteSlaveNegSyncLeaseDur          Integer32,
    f3PtpDynamicRemoteSlaveNegDelayRspLeaseDur      Integer32,
    f3PtpDynamicRemoteSlaveNegAnnounceLeaseDur      Integer32,
    f3PtpDynamicRemoteSlaveSyncDurRemTime           Unsigned32,
    f3PtpDynamicRemoteSlaveDelayRspDurRemTime       Unsigned32,
    f3PtpDynamicRemoteSlaveAnnounceDurRemTime       Unsigned32,
    f3PtpDynamicRemoteSlaveRowStatus                RowStatus,
    f3PtpDynamicRemoteSlaveStorageType              StorageType,
    f3PtpDynamicRemoteSlavePortIdentity             PortIdentity,
    f3PtpDynamicRemoteSlavePeerMacAddress           MacAddress,
    f3PtpDynamicRemoteSlaveIpV6Address              Ipv6Address
}

f3PtpDynamicRemoteSlaveIndex OBJECT-TYPE
    SYNTAX     Integer32
    MAX-ACCESS not-accessible 
    STATUS     current
    DESCRIPTION
         "Unique index value associated with the Remote Slave."
     ::= { f3PtpDynamicRemoteSlaveEntry 1 }

f3PtpDynamicRemoteSlaveAlias    OBJECT-TYPE
    SYNTAX      DisplayString (SIZE(0..256))
    MAX-ACCESS  read-write
    STATUS      current
    DESCRIPTION
         "This object allows SNMP management entities to provide an 
          alias to the Remote Slave."
     ::= { f3PtpDynamicRemoteSlaveEntry 2 }

f3PtpDynamicRemoteSlaveAdminState OBJECT-TYPE
    SYNTAX      AdminState 
    MAX-ACCESS  read-write
    STATUS      current
    DESCRIPTION
          "This object represents the Administrative State of the Remote Slave."
    ::= { f3PtpDynamicRemoteSlaveEntry 3 }

f3PtpDynamicRemoteSlaveOperationalState   OBJECT-TYPE
    SYNTAX      OperationalState 
    MAX-ACCESS  read-only
    STATUS      current
    DESCRIPTION
          "This object represents the Operational State of the Remote Slave."
    ::= { f3PtpDynamicRemoteSlaveEntry 4 }

f3PtpDynamicRemoteSlaveSecondaryState     OBJECT-TYPE
    SYNTAX      SecondaryState 
    MAX-ACCESS  read-only
    STATUS      current
    DESCRIPTION
           "This object represents the Secondary State of the Remote Slave."
    ::= { f3PtpDynamicRemoteSlaveEntry 5 }

f3PtpDynamicRemoteSlaveClockIdentity OBJECT-TYPE
    SYNTAX     ClockIdentity 
    MAX-ACCESS read-only
    STATUS     current
    DESCRIPTION
         "This object represents the Clock Identity of the Remote Slave."
     ::= { f3PtpDynamicRemoteSlaveEntry 6 }

f3PtpDynamicRemoteSlaveIpV4Address OBJECT-TYPE
    SYNTAX     IpAddress
    MAX-ACCESS read-only 
    STATUS     current
    DESCRIPTION
         "This object allows specification of the IPv4 Address of
          the Remote Slave."
     ::= { f3PtpDynamicRemoteSlaveEntry 7 }

f3PtpDynamicRemoteSlaveTimeCreated OBJECT-TYPE
    SYNTAX     DateAndTime
    MAX-ACCESS read-only 
    STATUS     current
    DESCRIPTION
         "This object presents time when this Remote Slave entity was created."
     ::= { f3PtpDynamicRemoteSlaveEntry 8 }

f3PtpDynamicRemoteSlaveSyncMsgRate OBJECT-TYPE
    SYNTAX     SyncMsgRate
    MAX-ACCESS read-only
    STATUS     current
    DESCRIPTION
         "This attribute specifies Sync Message Rate of the Remote Slave."
     ::= { f3PtpDynamicRemoteSlaveEntry 9 }

f3PtpDynamicRemoteSlaveDelayRspMsgRate OBJECT-TYPE
    SYNTAX     DelayRespMsgRate
    MAX-ACCESS read-only
    STATUS     current
    DESCRIPTION
         "This attribute specifies Delay Respone Message Rate of the Remote Slave."
     ::= { f3PtpDynamicRemoteSlaveEntry 10 }

f3PtpDynamicRemoteSlaveAnnounceMsgRate OBJECT-TYPE
    SYNTAX     AnnounceMsgRate
    MAX-ACCESS read-only
    STATUS     current
    DESCRIPTION
         "This attribute specifies Announce Message Rate of the Remote Slave."
     ::= { f3PtpDynamicRemoteSlaveEntry 11 }

f3PtpDynamicRemoteSlaveNegSyncLeaseDur OBJECT-TYPE
    SYNTAX     Integer32
    MAX-ACCESS read-only
    STATUS     current
    DESCRIPTION
         "This attribute indicates Sync messages negotiated Lease Duration in seconds."
     ::= { f3PtpDynamicRemoteSlaveEntry 12 }

f3PtpDynamicRemoteSlaveNegDelayRspLeaseDur OBJECT-TYPE
    SYNTAX     Integer32
    MAX-ACCESS read-only
    STATUS     current
    DESCRIPTION
         "This attribute indicates Delay Response messages negotiated Lease 
          Duration in seconds."
     ::= { f3PtpDynamicRemoteSlaveEntry 13 }

f3PtpDynamicRemoteSlaveNegAnnounceLeaseDur OBJECT-TYPE
    SYNTAX     Integer32
    MAX-ACCESS read-only
    STATUS     current
    DESCRIPTION
         "This attribute indicates Announce messages negotiated Lease 
          Duration in seconds."
     ::= { f3PtpDynamicRemoteSlaveEntry 14 }

f3PtpDynamicRemoteSlaveSyncDurRemTime OBJECT-TYPE
    SYNTAX     Unsigned32
    MAX-ACCESS read-only
    STATUS     current
    DESCRIPTION
         "This attribute indicates Remaining seconds of Lease Duration of Sync service."
     ::= { f3PtpDynamicRemoteSlaveEntry 15 }

f3PtpDynamicRemoteSlaveDelayRspDurRemTime OBJECT-TYPE
    SYNTAX     Unsigned32
    MAX-ACCESS read-only
    STATUS     current
    DESCRIPTION
         "This attribute indicates Remaining seconds of Lease Duration of Delay Response 
          service."
     ::= { f3PtpDynamicRemoteSlaveEntry 16 }

f3PtpDynamicRemoteSlaveAnnounceDurRemTime OBJECT-TYPE
    SYNTAX     Unsigned32
    MAX-ACCESS read-only
    STATUS     current
    DESCRIPTION
         "This attribute indicates Remaining seconds of Lease Duration of Announce 
          service."
     ::= { f3PtpDynamicRemoteSlaveEntry 17 }


f3PtpDynamicRemoteSlaveRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpDynamicRemoteSlaveRowStatus supported is
            destroy(6).  

            The f3PtpDynamicRemoteSlaveRowStatus object may be modified if
            the associated instance of this object is equal to active(1)."
    ::= { f3PtpDynamicRemoteSlaveEntry 18 }


f3PtpDynamicRemoteSlaveStorageType OBJECT-TYPE
    SYNTAX     StorageType
    MAX-ACCESS read-create
    STATUS     current
    DESCRIPTION
            "The type of storage configured for this entry."
    ::= { f3PtpDynamicRemoteSlaveEntry 19 }

f3PtpDynamicRemoteSlavePortIdentity OBJECT-TYPE
    SYNTAX     PortIdentity
    MAX-ACCESS read-only
    STATUS     current
    DESCRIPTION
            "The port identity of the remote slave"
    ::= { f3PtpDynamicRemoteSlaveEntry 20 }

f3PtpDynamicRemoteSlavePeerMacAddress OBJECT-TYPE
    SYNTAX     MacAddress
    MAX-ACCESS read-only
    STATUS     current
    DESCRIPTION
            "The port identity of the remote slave"
    ::= { f3PtpDynamicRemoteSlaveEntry 21 }

f3PtpDynamicRemoteSlaveIpV6Address OBJECT-TYPE
    SYNTAX     Ipv6Address 
    MAX-ACCESS read-only
    STATUS   current
    DESCRIPTION
         "This object allows specification of the unicast IPv6 Address of
          the Remote Slave."
    ::= { f3PtpDynamicRemoteSlaveEntry 22 }





--
-- Ethernet Traffic Port - PTP Flow Point Table
--
f3PtpTrafficPortFlowPointTable OBJECT-TYPE
    SYNTAX     SEQUENCE OF F3PtpTrafficPortFlowPointEntry 
    MAX-ACCESS not-accessible
    STATUS     current
    DESCRIPTION
       "A list of entries corresponding to the PTP Access Port Flow Point
        entities."
    ::= { f3PtpConfigObjects 17}

f3PtpTrafficPortFlowPointEntry OBJECT-TYPE
    SYNTAX     F3PtpTrafficPortFlowPointEntry
    MAX-ACCESS not-accessible
    STATUS     current
    DESCRIPTION
          "An entry containing information applicable to a particular
           Traffic Port Flow Point Entity."
    INDEX { neIndex, shelfIndex, slotIndex, cmEthernetTrafficPortIndex, 
            f3PtpTrafficPortFlowPointIndex }
    ::= { f3PtpTrafficPortFlowPointTable 1 }

F3PtpTrafficPortFlowPointEntry ::= SEQUENCE {
    f3PtpTrafficPortFlowPointIndex                 Integer32,
    f3PtpTrafficPortFlowPointAlias                 DisplayString,

    f3PtpTrafficPortFlowPointAdminState            AdminState,
    f3PtpTrafficPortFlowPointOperationalState      OperationalState,
    f3PtpTrafficPortFlowPointSecondaryState        SecondaryState,

    f3PtpTrafficPortFlowPointType                  PtpFlowPointType,
    f3PtpTrafficPortFlowPointClock                 VariablePointer,
    f3PtpTrafficPortFlowPointService               VariablePointer,
    f3PtpTrafficPortFlowPointOuterVlanEtherType    Integer32,
    f3PtpTrafficPortFlowPointOuterVlanMemberList   DisplayString,
    f3PtpTrafficPortFlowPointOuterUntaggedEnabled  TruthValue,
    f3PtpTrafficPortFlowPointInner1VlanEtherType   Integer32,
    f3PtpTrafficPortFlowPointInner1VlanMemberList  DisplayString,
    f3PtpTrafficPortFlowPointInner1UntaggedEnabled TruthValue,
    f3PtpTrafficPortFlowPointInner2VlanEtherType   Integer32,
    f3PtpTrafficPortFlowPointInner2VlanMemberList  DisplayString,
    f3PtpTrafficPortFlowPointInner2UntaggedEnabled TruthValue,

    f3PtpTrafficPortFlowPointStorageType           StorageType,
    f3PtpTrafficPortFlowPointRowStatus             RowStatus,
    f3PtpTrafficPortFlowPointCOS                   Integer32,
    f3PtpTrafficPortFlowPointCIRLo                 Unsigned32,
    f3PtpTrafficPortFlowPointCIRHi                 Unsigned32,
    f3PtpTrafficPortFlowPointEIRLo                 Unsigned32,
    f3PtpTrafficPortFlowPointEIRHi                 Unsigned32,
    f3PtpTrafficPortFlowPointAssociatedQueueProfile  VariablePointer,
    f3PtpTrafficPortFlowPointLoopAvoidance           VariablePointer
}

f3PtpTrafficPortFlowPointIndex OBJECT-TYPE
    SYNTAX     Integer32
    MAX-ACCESS not-accessible 
    STATUS     current
    DESCRIPTION
         "Unique index value associated with the Traffic Port PTP Flow Point."
     ::= { f3PtpTrafficPortFlowPointEntry 1 }

f3PtpTrafficPortFlowPointAlias OBJECT-TYPE
    SYNTAX      DisplayString (SIZE(0..256))
    MAX-ACCESS  read-create
    STATUS      current
    DESCRIPTION
         "This object allows SNMP management entities to provide an 
          alias to the Traffic Port PTP Flow Point."
     ::= { f3PtpTrafficPortFlowPointEntry 2 }

f3PtpTrafficPortFlowPointAdminState OBJECT-TYPE
    SYNTAX      AdminState 
    MAX-ACCESS  read-write
    STATUS      current
    DESCRIPTION
            "This object represents the Administrative State of the 
             PTP Flow Point." 
     ::= { f3PtpTrafficPortFlowPointEntry 3 }

f3PtpTrafficPortFlowPointOperationalState   OBJECT-TYPE
    SYNTAX      OperationalState 
    MAX-ACCESS  read-only
    STATUS      current
    DESCRIPTION
            "This object represents the Operational State of the PTP Flow 
             Point."
     ::= { f3PtpTrafficPortFlowPointEntry 4 }

f3PtpTrafficPortFlowPointSecondaryState     OBJECT-TYPE
    SYNTAX      SecondaryState 
    MAX-ACCESS  read-only
    STATUS      current
    DESCRIPTION
           "This object represents the Secondary State of the PTP Flow Point."
     ::= { f3PtpTrafficPortFlowPointEntry 5 }

f3PtpTrafficPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpTrafficPortFlowPointEntry 6 }

f3PtpTrafficPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpTrafficPortFlowPointEntry 7 }

f3PtpTrafficPortFlowPointService OBJECT-TYPE
    SYNTAX      VariablePointer 
    MAX-ACCESS  read-create
    STATUS      current
    DESCRIPTION
            "This object points to the associated Traffic Service Flow."
    ::= { f3PtpTrafficPortFlowPointEntry 8 }

f3PtpTrafficPortFlowPointOuterVlanEtherType OBJECT-TYPE
    SYNTAX      Integer32 
    MAX-ACCESS  read-create
    STATUS      current
    DESCRIPTION
            "This object allows specification of the Outer VLAN Ether Type
             of the PTP Flow."
    ::= { f3PtpTrafficPortFlowPointEntry 9 }

f3PtpTrafficPortFlowPointOuterVlanMemberList OBJECT-TYPE
    SYNTAX      DisplayString 
    MAX-ACCESS  read-create
    STATUS      current
    DESCRIPTION
            "This object allows specification of the Outer VLAN(s) 
             of the PTP Flow."
    ::= { f3PtpTrafficPortFlowPointEntry 10 }

f3PtpTrafficPortFlowPointOuterUntaggedEnabled OBJECT-TYPE
    SYNTAX      TruthValue 
    MAX-ACCESS  read-create
    STATUS      current
    DESCRIPTION
            "This object allows specification of whether the Outer VLAN
             exists or not." 
    ::= { f3PtpTrafficPortFlowPointEntry 11 }

f3PtpTrafficPortFlowPointInner1VlanEtherType OBJECT-TYPE
    SYNTAX      Integer32 
    MAX-ACCESS  read-create
    STATUS      current
    DESCRIPTION
            "This object allows specification of the Inner1 VLAN Ether Type
             of the PTP Flow."
    ::= { f3PtpTrafficPortFlowPointEntry 12 }

f3PtpTrafficPortFlowPointInner1VlanMemberList OBJECT-TYPE
    SYNTAX      DisplayString 
    MAX-ACCESS  read-create
    STATUS      current
    DESCRIPTION
            "This object allows specification of the Inner1 VLAN(s) 
             of the PTP Flow."
    ::= { f3PtpTrafficPortFlowPointEntry 13 }

f3PtpTrafficPortFlowPointInner1UntaggedEnabled OBJECT-TYPE
    SYNTAX      TruthValue 
    MAX-ACCESS  read-create
    STATUS      current
    DESCRIPTION
            "This object allows specification of whether the Inner1 VLAN
             exists or not." 
    ::= { f3PtpTrafficPortFlowPointEntry 14 }

f3PtpTrafficPortFlowPointInner2VlanEtherType OBJECT-TYPE
    SYNTAX      Integer32 
    MAX-ACCESS  read-create
    STATUS      current
    DESCRIPTION
            "This object allows specification of the Inner2 VLAN Ether Type
             of the PTP Flow."
    ::= { f3PtpTrafficPortFlowPointEntry 15 }

f3PtpTrafficPortFlowPointInner2VlanMemberList OBJECT-TYPE
    SYNTAX      DisplayString 
    MAX-ACCESS  read-create
    STATUS      current
    DESCRIPTION
            "This object allows specification of the Inner2 VLAN(s) 
             of the PTP Flow."
    ::= { f3PtpTrafficPortFlowPointEntry 16 }

f3PtpTrafficPortFlowPointInner2UntaggedEnabled OBJECT-TYPE
    SYNTAX      TruthValue 
    MAX-ACCESS  read-create
    STATUS      current
    DESCRIPTION
            "This object allows specification of whether the Inner1 VLAN
             exists or not." 
    ::= { f3PtpTrafficPortFlowPointEntry 17 }

f3PtpTrafficPortFlowPointStorageType OBJECT-TYPE
    SYNTAX     StorageType
    MAX-ACCESS read-create
    STATUS     current
    DESCRIPTION
            "The type of storage configured for this entry."
    ::= { f3PtpTrafficPortFlowPointEntry 18 }

f3PtpTrafficPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTrafficPortFlowPointRowStatus supported are
            createAndGo(4) and destroy(6).  All mandatory attributes
            must be specified in a single SNMP SET request with
            f3PtpTrafficPortFlowPointRowStatus value as createAndGo(4).
            Upon successful row creation, this object has a
            value of active(1).

            The f3PtpTrafficPortFlowPointRowStatus object may be modified if
            the associated instance of this object is equal to active(1)."
    ::= { f3PtpTrafficPortFlowPointEntry 19 }


f3PtpTrafficPortFlowPointCOS OBJECT-TYPE
    SYNTAX      Integer32 (0..7)
    MAX-ACCESS  read-create
    STATUS      current
    DESCRIPTION
            "This object allows specification of Class of Service of the PTP traffic
             associated with this Flow Point."
    ::= { f3PtpTrafficPortFlowPointEntry 20 }

f3PtpTrafficPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpTrafficPortFlowPointEntry 21 }

f3PtpTrafficPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpTrafficPortFlowPointEntry 22 }

f3PtpTrafficPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpTrafficPortFlowPointEntry 23 }

f3PtpTrafficPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpTrafficPortFlowPointEntry 24 }

f3PtpTrafficPortFlowPointAssociatedQueueProfile OBJECT-TYPE
    SYNTAX      VariablePointer
    MAX-ACCESS  read-create
    STATUS      current
    DESCRIPTION
            "This object allows specification of the related queue profile."
    ::= { f3PtpTrafficPortFlowPointEntry 25 }

--- Not in OSA
f3PtpTrafficPortFlowPointLoopAvoidance OBJECT-TYPE
    SYNTAX      VariablePointer
    MAX-ACCESS  read-create
    STATUS      current
    DESCRIPTION
            "This object allows specify OID of this associated Loop Avoidance protocol entity."
    ::= { f3PtpTrafficPortFlowPointEntry 26 }

--
-- traffic port ext talbe
--
f3PtpEthernetTrafficPortExtTable  OBJECT-TYPE
    SYNTAX      SEQUENCE OF F3PtpEthernetTrafficPortExtEntry
    MAX-ACCESS  not-accessible
    STATUS      current
    DESCRIPTION
            "This table extends cmEthernetTrafficPortTable by adding PTP related parameters."
    ::= { f3PtpConfigObjects 18 }

f3PtpEthernetTrafficPortExtEntry OBJECT-TYPE
    SYNTAX      F3PtpEthernetTrafficPortExtEntry
    MAX-ACCESS  not-accessible
    STATUS      current
    DESCRIPTION
            "A conceptual row in the f3PtpEthernetTrafficPortExtTable."
    AUGMENTS { cmEthernetTrafficPortEntry }
    ::= { f3PtpEthernetTrafficPortExtTable 1 }

F3PtpEthernetTrafficPortExtEntry ::= SEQUENCE {
    f3PtpEthernetTrafficPortDelayAsymmetry Integer32
}

f3PtpEthernetTrafficPortDelayAsymmetry OBJECT-TYPE
     SYNTAX     Integer32
     MAX-ACCESS read-write
     STATUS     current
     DESCRIPTION
         "This object allows configuring Delay Asymmetry in nanoseconds on 
          the Ethernet Traffic Port. The default value is 0."
     ::= { f3PtpEthernetTrafficPortExtEntry 1 }

--
-- PTP Clock Table
--
f3PtpPTPClockTable OBJECT-TYPE
    SYNTAX     SEQUENCE OF F3PtpPTPClockEntry
    MAX-ACCESS not-accessible
    STATUS     current
    DESCRIPTION
       "A list of entries corresponding to the PTP PTP Clock entities."
    ::= { f3PtpConfigObjects 19 }

f3PtpPTPClockEntry OBJECT-TYPE
    SYNTAX     F3PtpPTPClockEntry
    MAX-ACCESS not-accessible
    STATUS     current
    DESCRIPTION
          "An entry containing information applicable to a particular
           PTP Clock Entity."
    INDEX { neIndex, f3PtpPTPClockIndex}
            
    ::= { f3PtpPTPClockTable 1 }


F3PtpPTPClockEntry ::= SEQUENCE {
    f3PtpPTPClockIndex                              Integer32,
    f3PtpPTPClockAdminState                         AdminState,           
    f3PtpPTPClockAlias                              DisplayString,
    f3PtpPTPClockOperationalState                   OperationalState,  
    f3PtpPTPClockSecondaryState                     SecondaryState,
    f3PtpPTPClockProfile                            PTPClockProfile,  
    f3PtpPTPClockClockType                          PTPClockType,    
    f3PtpPTPClockOperationalMode                    PTPClockOperMode,  
    f3PtpPTPClockClockIdentity                      ClockIdentity,  
    f3PtpPTPClockDomainNumber                       Integer32, 
    f3PtpPTPClockTimeSource                         VariablePointer,  
    f3PtpPTPClockPriority1                          Unsigned32,                         
    f3PtpPTPClockPriority2                          Unsigned32,  
    f3PtpPTPClockLocalPriority                      Unsigned32,     
    f3PtpPTPClockClockAccuracy                      Unsigned32, 
    f3PtpPTPClockScaledLogVariance                  Integer32, 
    f3PtpPTPClockSyncEid                            VariablePointer,  
    f3PtpPTPClockCurrentTimeOfDay                   DateAndTime,  
    f3PtpPTPClockActiveSlavePort                    VariablePointer, 
    f3PtpPTPClockClockRecoveryState                 ClockRecoveryState, 
    f3PtpPTPClockPhaseRecoveryState                 PhaseRecoveryState, 
    f3PtpPTPClockTimeTraceabilityStatus             TruthValue,   
    f3PtpPTPClockTimeSinceTimeTraceabilityChanged   Unsigned32, 
    f3PtpPTPClockFreqTraceabilityStatus             TruthValue,                           
    f3PtpPTPClockTimeSinceFreqTraceabilityChanged   Unsigned32, 

    f3PtpPTPClockClockSyncEEnabled                  TruthValue,
    f3PtpPTPClockClockQLModeEnabled                 TruthValue,
    f3PtpPTPClockClockExpectedQL                    SSMQualityLevel,
    f3PtpPTPClockClockAssumedQL                     SSMQualityLevel,
    f3PtpPTPClockClockReceivedQL                    SSMQualityLevel,



    f3PtpPTPClockStorageType                        StorageType,
    f3PtpPTPClockRowStatus                          RowStatus,
    f3PtpPTPClockCurrentOffsetFromMaster            PerfCounter64,
    f3PtpPTPClockRecentMeanPathDelay                PerfCounter64,
    f3PtpPTPClockRecentSyncPDV                      PerfCounter64,
    f3PtpPTPClockClockClass                         Unsigned32,
    f3PtpPTPClockPhysicalEntityIndex                Integer32,
    f3PtpPTPClockActiveGrantsAnnounceService        Integer32,
    f3PtpPTPClockActiveGrantsSyncService            Integer32,
    f3PtpPTPClockActiveGrantsDelayRequestService    Integer32,
    f3PtpPTPClockMaxStepRemoved                     Integer32,
    f3PtpPTPClockServiceAvailableTime               Unsigned32,
    f3PtpPTPClockServiceUnavailableTime             Unsigned32,
    f3PtpPTPClockServiceAvailablePercentage         DisplayString,
    f3PtpPTPClockGrandMasterID                      Integer32,
    f3PtpPTPClockTimeInaccuracy                     Unsigned32,
    f3PtpPTPClockNetworkTimeInaccuracy              Unsigned32,
    f3PtpPTPClockApplicationMode                    ProfileApplicationMode,
    f3PtpPTPClockRecoveryMode                       ClockRecoveryMode,
    f3PtpPTPClockCurrentOffsetFromMasterScaled      ScaledNanoseconds,
    f3PtpPTPClockRecentMeanPathDelayScaled          ScaledNanoseconds,
    f3PtpPTPClockRecentSyncPDVScaled                ScaledNanoseconds,
    f3PtpSynchronizationNotAssured                  TruthValue
}


f3PtpPTPClockIndex OBJECT-TYPE
    SYNTAX     Integer32
    MAX-ACCESS not-accessible 
    STATUS     current
    DESCRIPTION
         "Unique index value associated with the PTP Clock Entity."
     ::= { f3PtpPTPClockEntry 1 }


f3PtpPTPClockAdminState OBJECT-TYPE
    SYNTAX      AdminState 
    MAX-ACCESS  read-write
    STATUS      current
    DESCRIPTION
          "This object represents the Administrative State of the PTP Clock."
    ::= { f3PtpPTPClockEntry 2 }

f3PtpPTPClockAlias    OBJECT-TYPE
    SYNTAX      DisplayString (SIZE(0..256))
    MAX-ACCESS  read-write
    STATUS      current
    DESCRIPTION
         "This object allows SNMP management entities to provide an 
          alias to the PTP Clock entity."
     ::= { f3PtpPTPClockEntry 3 }


f3PtpPTPClockOperationalState   OBJECT-TYPE
    SYNTAX      OperationalState 
    MAX-ACCESS  read-only
    STATUS      current
    DESCRIPTION
          "This object represents the Operational State of the PTP Clock." 
    ::= { f3PtpPTPClockEntry 4 }

f3PtpPTPClockSecondaryState     OBJECT-TYPE
    SYNTAX      SecondaryState 
    MAX-ACCESS  read-only
    STATUS      current
    DESCRIPTION
           "This object represents the Secondary State of the PTP Clock."
    ::= { f3PtpPTPClockEntry 5 }

f3PtpPTPClockProfile     OBJECT-TYPE
    SYNTAX      PTPClockProfile 
    MAX-ACCESS  read-create
    STATUS      current
    DESCRIPTION
           "This object represents the Secondary State of the PTP Clock."
    ::= { f3PtpPTPClockEntry 6 }


f3PtpPTPClockClockType OBJECT-TYPE
    SYNTAX     PTPClockType 
    MAX-ACCESS read-create
    STATUS     current
    DESCRIPTION
         "This object provides the entry from the f3TimeClockTable, which is
          used as frequency and time of day source this Master Clock."
     ::= { f3PtpPTPClockEntry 7 }

f3PtpPTPClockOperationalMode OBJECT-TYPE
    SYNTAX     PTPClockOperMode 
    MAX-ACCESS read-only
    STATUS     current
    DESCRIPTION
         "This object provides the entry from the f3TimeClockTable, which is
          used as frequency and time of day source this Master Clock."
     ::= { f3PtpPTPClockEntry 8 }

f3PtpPTPClockClockIdentity OBJECT-TYPE
    SYNTAX     ClockIdentity 
    MAX-ACCESS read-create
    STATUS     current
    DESCRIPTION
         "This object specifies the Clock Identity of the PTP Clock." 
     ::= { f3PtpPTPClockEntry 9 }

f3PtpPTPClockDomainNumber OBJECT-TYPE
    SYNTAX     Integer32 
    MAX-ACCESS read-create
    STATUS     current
    DESCRIPTION
          "This object allows specification of the PTP domain number of the
           Master Clock ."
     ::= { f3PtpPTPClockEntry 10 }

f3PtpPTPClockTimeSource OBJECT-TYPE
    SYNTAX      VariablePointer
    MAX-ACCESS  read-only
    STATUS      current
    DESCRIPTION
           "This object specify PTP Clock time source."
    ::= { f3PtpPTPClockEntry 11 }
 
f3PtpPTPClockPriority1 OBJECT-TYPE
    SYNTAX     Unsigned32 (0..255) 
    MAX-ACCESS read-write
    STATUS     current
    DESCRIPTION
         ""
     ::= { f3PtpPTPClockEntry 12 }
     
f3PtpPTPClockPriority2 OBJECT-TYPE
    SYNTAX     Unsigned32 (0..255) 
    MAX-ACCESS read-write
    STATUS     current
    DESCRIPTION
         ""
     ::= { f3PtpPTPClockEntry 13 }

f3PtpPTPClockLocalPriority OBJECT-TYPE
    SYNTAX     Unsigned32 (1..255) 
    MAX-ACCESS read-write
    STATUS     current
    DESCRIPTION
        "This object allows configuration of  local priority used by the PTP Clock." 
     ::= { f3PtpPTPClockEntry 14 }
     
     
f3PtpPTPClockClockAccuracy OBJECT-TYPE
    SYNTAX     Unsigned32 
    MAX-ACCESS read-only
    STATUS     obsolete
    DESCRIPTION
         "This object indicates Clock accuracy of the clock"
     ::= { f3PtpPTPClockEntry 15 }

f3PtpPTPClockScaledLogVariance   OBJECT-TYPE
    SYNTAX      Integer32 
    MAX-ACCESS  read-only
    STATUS      current
    DESCRIPTION
          "" 
    ::= { f3PtpPTPClockEntry 16 }

f3PtpPTPClockSyncEid OBJECT-TYPE
    SYNTAX     VariablePointer 
    MAX-ACCESS read-write
    STATUS     current
    DESCRIPTION
         "This object provides the entry from the f3SyncTable, which is
          used as frequency for this PTP Clock."
     ::= { f3PtpPTPClockEntry 17 }

f3PtpPTPClockCurrentTimeOfDay OBJECT-TYPE
    SYNTAX     DateAndTime 
    MAX-ACCESS read-only
    STATUS     current
    DESCRIPTION
         "This object allows specification of the PTP Clock Current
          Time of Day." 
     ::= { f3PtpPTPClockEntry 18 }

f3PtpPTPClockActiveSlavePort OBJECT-TYPE
    SYNTAX     VariablePointer 
    MAX-ACCESS read-only
    STATUS     current
    DESCRIPTION
         "This object specifies Active Slave Port of the PTP Clock."
     ::= { f3PtpPTPClockEntry 19 }

f3PtpPTPClockClockRecoveryState    OBJECT-TYPE 
    SYNTAX     ClockRecoveryState 
    MAX-ACCESS read-only
    STATUS     current
    DESCRIPTION
         "This object provides the TPTP Clock's clock recovery state." 
     ::= { f3PtpPTPClockEntry 20 }

f3PtpPTPClockPhaseRecoveryState OBJECT-TYPE
    SYNTAX      PhaseRecoveryState
    MAX-ACCESS  read-only
    STATUS      current
    DESCRIPTION
           "This object specify the phase recovery state."
    ::= { f3PtpPTPClockEntry 21 }
    
f3PtpPTPClockTimeTraceabilityStatus OBJECT-TYPE
    SYNTAX      TruthValue
    MAX-ACCESS  read-only
    STATUS      current
    DESCRIPTION
           "This object provides the Time traceability status of the
            PTP Clock."
    ::= { f3PtpPTPClockEntry 22 }


f3PtpPTPClockTimeSinceTimeTraceabilityChanged OBJECT-TYPE
    SYNTAX      Unsigned32
    MAX-ACCESS  read-only
    STATUS      current
    DESCRIPTION
           "This object provides the time in seconds since the Time traceability 
            changed on the PTP Clock."
    ::= { f3PtpPTPClockEntry 23 }

f3PtpPTPClockFreqTraceabilityStatus OBJECT-TYPE
    SYNTAX      TruthValue
    MAX-ACCESS  read-only
    STATUS      current
    DESCRIPTION
           "This object provides the Frequency traceability status of the
            PTP Clock."
    ::= { f3PtpPTPClockEntry 24 }

f3PtpPTPClockTimeSinceFreqTraceabilityChanged OBJECT-TYPE
    SYNTAX      Unsigned32
    MAX-ACCESS  read-only
    STATUS      current
    DESCRIPTION
           "This object provides the time in seconds since the Frequency traceability 
            changed on the PTP Clock."
    ::= { f3PtpPTPClockEntry 25 }
    
--Synchronous Port params
f3PtpPTPClockClockSyncEEnabled OBJECT-TYPE 
    SYNTAX     TruthValue
    MAX-ACCESS read-write
    STATUS     current
    DESCRIPTION
         "This object allows to specify whether the Telecom Slave 
          can be enabled/disabled for Synchronous Ethernet. 
          When enabled, on receive side 
            -telecom slave can extract the frequency 
             and pass the recovered clock to the system clock
            -QL is extracted (when QL is enabled) from the selected SOOC's clock class
            -telecom slave is eligible to be selected as a system clock reference
          When disabled, on receive side,
            -telecom slave does not pass the recovered clock to the system clock 
            -telecom slave does not process the QL from selected SOOC's clock class 
            -telecom slave is not eligible to be selected as a 
                     system clock reference."
     ::= { f3PtpPTPClockEntry 26 }

f3PtpPTPClockClockQLModeEnabled OBJECT-TYPE 
    SYNTAX     TruthValue
    MAX-ACCESS read-write
    STATUS     current
    DESCRIPTION
         "This object allows to specify whether the Telecom Slave 
          can be enabled/disabled for QL Mode.  
          When enabled, on receive side 
            -telecom slave can extract the QL from selected SOOC's clock class 
          When disabled, on receive side,
            -telecom slave does not process the QL from selected SOOC's clock class."
     ::= { f3PtpPTPClockEntry 27 }

f3PtpPTPClockClockExpectedQL OBJECT-TYPE 
    SYNTAX     SSMQualityLevel
    MAX-ACCESS read-write
    STATUS     current
    DESCRIPTION
         "This object allows to specify the expected QL when the 
          Telecom Slave is enabled for QL Mode.  This is applicable 
          when f3PtpPTPClockClockQLModeEnabled is set to true.
          This object allows the user to set a minimum
          expected received Quality Level on the Telecom Slave. 
          The valid values depend upon the SYNC entity's Network Clock Type. 
          A value of None represents that a minimum Quality Level is not expected. 
          The default value shall be None."
     ::= { f3PtpPTPClockEntry 28 }

f3PtpPTPClockClockAssumedQL OBJECT-TYPE 
    SYNTAX     SSMQualityLevel
    MAX-ACCESS read-write
    STATUS     current
    DESCRIPTION
         "This object allows to specify the assumed QL on the 
          Telecom Slave.  The Assumed QL is only meaningful if the Network Clock Type
          (see fsp150cm-sync.mib) is option1 and the 
          telecom slave's QL Mode is disabled and the telecom slave is being used as 
          an input reference source. Under these conditions,
          the specified QL value is assumed to be the Quality Level of the
          non-failed reference."
     ::= { f3PtpPTPClockEntry 29 }

f3PtpPTPClockClockReceivedQL OBJECT-TYPE 
    SYNTAX     SSMQualityLevel
    MAX-ACCESS read-only
    STATUS     current
    DESCRIPTION
         "This object provides the Received QL value for the Telecom Slave. 
          If the Telecom Slave's QL Mode is disabled, then the received 
          QL value is not applicable."
     ::= { f3PtpPTPClockEntry 30 }


f3PtpPTPClockStorageType OBJECT-TYPE
    SYNTAX     StorageType
    MAX-ACCESS read-create
    STATUS     current
    DESCRIPTION
            "The type of storage configured for this entry."
    ::= { f3PtpPTPClockEntry 31 }

f3PtpPTPClockRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpPTPClockRowStatus supported are
            createAndGo(4) and destroy(6).  All mandatory attributes
            must be specified in a single SNMP SET request with
            f3PtpPTPClockRowStatus value as createAndGo(4).
            Upon successful row creation, this object has a
            value of active(1).

            The f3PtpPTPClockRowStatus object may be modified if
            the associated instance of this object is equal to active(1)."
    ::= { f3PtpPTPClockEntry 32 }
     
f3PtpPTPClockCurrentOffsetFromMaster OBJECT-TYPE 
    SYNTAX     PerfCounter64
    MAX-ACCESS read-only
    STATUS     current
    DESCRIPTION
         "This object provides the value for current offset from master.
          Note: the SYNTAX should be ScaledNanoseconds."
     ::= { f3PtpPTPClockEntry 33 }

f3PtpPTPClockRecentMeanPathDelay OBJECT-TYPE 
    SYNTAX     PerfCounter64
    MAX-ACCESS read-only
    STATUS     current
    DESCRIPTION
         "This object provides recent mean path delay.
          Note: the SYNTAX should be ScaledNanoseconds."
     ::= { f3PtpPTPClockEntry 34 }

f3PtpPTPClockRecentSyncPDV OBJECT-TYPE 
    SYNTAX     PerfCounter64
    MAX-ACCESS read-only
    STATUS     current
    DESCRIPTION
         "This object provides the recent Sync messages packet delay variation.
          Note: the SYNTAX should be ScaledNanoseconds."
     ::= { f3PtpPTPClockEntry 35 }

f3PtpPTPClockClockClass OBJECT-TYPE 
    SYNTAX     Unsigned32
    MAX-ACCESS read-only
    STATUS     current
    DESCRIPTION
         "This object specify PTP Clock class"
     ::= { f3PtpPTPClockEntry 36 }

f3PtpPTPClockPhysicalEntityIndex OBJECT-TYPE 
    SYNTAX     Integer32
    MAX-ACCESS read-only
    STATUS     current
    DESCRIPTION
         "Populated with index into the physEntityTable (always point to left card slot in case of protection)"
     ::= { f3PtpPTPClockEntry 37 }

f3PtpPTPClockActiveGrantsAnnounceService OBJECT-TYPE 
    SYNTAX     Integer32
    MAX-ACCESS read-only
    STATUS     current
    DESCRIPTION
         "Report number of active grants announce service."
     ::= { f3PtpPTPClockEntry 38 }

f3PtpPTPClockActiveGrantsSyncService OBJECT-TYPE 
    SYNTAX     Integer32
    MAX-ACCESS read-only
    STATUS     current
    DESCRIPTION
         "Report number of active grants sync service."
     ::= { f3PtpPTPClockEntry 39 }

f3PtpPTPClockActiveGrantsDelayRequestService OBJECT-TYPE 
    SYNTAX     Integer32
    MAX-ACCESS read-only
    STATUS     current
    DESCRIPTION
         "Report number of active grants delay-request service."
     ::= { f3PtpPTPClockEntry 40 }

f3PtpPTPClockMaxStepRemoved OBJECT-TYPE 
    SYNTAX     Integer32
    MAX-ACCESS read-write
    STATUS     current
    DESCRIPTION
         "Local PTP Clock only qualify the announce message with the value less than configured."
     ::= { f3PtpPTPClockEntry 41 }

f3PtpPTPClockServiceAvailableTime OBJECT-TYPE
    SYNTAX     Unsigned32
    MAX-ACCESS read-only
    STATUS     current
    DESCRIPTION
            "This object allows to manage service available time (seconds) for PTP."
    ::= { f3PtpPTPClockEntry 42 }

f3PtpPTPClockServiceUnavailableTime OBJECT-TYPE
    SYNTAX     Unsigned32
    MAX-ACCESS read-only
    STATUS     current
    DESCRIPTION
            "This object allows to manage service unavailable  time (seconds) for PTP."
    ::= { f3PtpPTPClockEntry 43 }

f3PtpPTPClockServiceAvailablePercentage OBJECT-TYPE
    SYNTAX     DisplayString
    MAX-ACCESS read-only
    STATUS     current
    DESCRIPTION
            "This object allows to manage service available in percentage [XXX.YY%] for PTP."
    ::= { f3PtpPTPClockEntry 44 }

f3PtpPTPClockGrandMasterID OBJECT-TYPE
    SYNTAX     Integer32 (0..65535)
    MAX-ACCESS read-write
    STATUS     current
    DESCRIPTION
            "Grandmaster Identity to be transmitted in IEEE_C37_238 TLV (2 bytes). Most significant byte is reserved and shall be 0.
             Configurable for grandmaster-capable devices only. Note: the range for c37-238-2011 is (3..254)"
    ::= { f3PtpPTPClockEntry 45 }

f3PtpPTPClockTimeInaccuracy OBJECT-TYPE
    SYNTAX     Unsigned32
    MAX-ACCESS read-write
    STATUS     current
    DESCRIPTION
            "networkTimeInaccuracy to be transmitted in IEEE_C37_238 TLV. This value is set at the grandmaster-capable clocks."
    ::= { f3PtpPTPClockEntry 46 }

f3PtpPTPClockNetworkTimeInaccuracy OBJECT-TYPE
    SYNTAX     Unsigned32
    MAX-ACCESS read-write
    STATUS     current
    DESCRIPTION
            "Maximum TimeInaccuracy that the device contributes to the networkTimeInaccuracy."
    ::= { f3PtpPTPClockEntry 47 }

f3PtpPTPClockApplicationMode OBJECT-TYPE
    SYNTAX     ProfileApplicationMode
    MAX-ACCESS read-create
    STATUS     current
    DESCRIPTION
            "This object is used to set Telecom Slave application mode."
    ::= { f3PtpPTPClockEntry 48 }
	
f3PtpPTPClockRecoveryMode OBJECT-TYPE
    SYNTAX     ClockRecoveryMode
    MAX-ACCESS read-create
    STATUS     current
    DESCRIPTION
            "This object allows specification of whether the Clock Recovery Mode
          is one-way or two-way.  In one-way mode, only Sync messages are
          used for frequency recovery.  In two-way mode, both Sync and 
          Delay Request-Response messages are used for measuring the mean path delay."
    ::= { f3PtpPTPClockEntry 49 }

f3PtpPTPClockCurrentOffsetFromMasterScaled OBJECT-TYPE
    SYNTAX     ScaledNanoseconds 
    MAX-ACCESS read-only
    STATUS     current
    DESCRIPTION
        "This object provides the current Offset From Master.
         The value provided is in nanoseconds." 
     ::= { f3PtpPTPClockEntry 50 }

f3PtpPTPClockRecentMeanPathDelayScaled OBJECT-TYPE
    SYNTAX     ScaledNanoseconds  
    MAX-ACCESS read-only
    STATUS     current
    DESCRIPTION
        "This object provides the most recent 
         mean path delay." 
     ::= { f3PtpPTPClockEntry 51 }

f3PtpPTPClockRecentSyncPDVScaled OBJECT-TYPE
    SYNTAX     ScaledNanoseconds  
    MAX-ACCESS read-only
    STATUS     current
    DESCRIPTION
        "This object provides the Sync messages 
         packet delay."
     ::= { f3PtpPTPClockEntry 52 }
                       

f3PtpSynchronizationNotAssured OBJECT-TYPE
    SYNTAX     TruthValue  
    MAX-ACCESS read-only
    STATUS     current
    DESCRIPTION
        "This object indicates if the synchronization is assured."
     ::= { f3PtpPTPClockEntry 53 }
   

--
-- PTP Port Table      
--
f3PtpPTPPortTable OBJECT-TYPE
    SYNTAX     SEQUENCE OF F3PtpPTPPortEntry
    MAX-ACCESS not-accessible
    STATUS     current
    DESCRIPTION
       "A list of entries corresponding to the PTP PTP Port entities."
    ::= { f3PtpConfigObjects 20 }

f3PtpPTPPortEntry OBJECT-TYPE
    SYNTAX     F3PtpPTPPortEntry
    MAX-ACCESS not-accessible
    STATUS     current
    DESCRIPTION
          "An entry containing information applicable to a particular
           PTP Port Entity."
    INDEX { neIndex, f3PtpPTPClockIndex,f3PtpPTPPortIndex}
            
    ::= { f3PtpPTPPortTable 1 }


F3PtpPTPPortEntry ::= SEQUENCE {
    f3PtpPTPPortIndex                              Integer32,
    f3PtpPTPPortAdminState                         AdminState,
    f3PtpPTPPortAlias                              DisplayString,          
    f3PtpPTPPortOperationalState                   OperationalState,  
    f3PtpPTPPortSecondaryState                     SecondaryState,
    f3PtpPTPPortPeerPortIdentity                   PortIdentity,
    f3PtpPTPPortLocalPriority                      Unsigned32,     
    f3PtpPTPPortPtpFlowPointEid                    VariablePointer,   
    f3PtpPTPPortNotSlave                           TruthValue,   
    f3PtpPTPPortTxDestMacAddress                   DestMacAddrType,   
    f3PtpPTPPortSyncMessageRate                    SyncMessageRate,   
    f3PtpPTPPortmDelayReqRespMsgRate               DelayReqMessageRate,
    f3PtpPTPPortmAnnounceMsgRate                   AnnounceMessageRate,
    f3PtpPTPPortAnnounceReceiptTimeout             Integer32,                            
    f3PtpPTPPortSyncReceiptTimeout                 Integer32,                            
    f3PtpPTPPortDelayRespTimeout                   Integer32,  
    f3PtpPTPPortPortState                          PtpPortState,
    f3PtpPTPPortBmcaDecisionCode                   BMCARole, 
    f3PtpPTPPortClockClass                         Unsigned32, 
    f3PtpPTPPortPeerPortMacAddress                 MacAddress,
    f3PtpPTPPortRowStatus                          RowStatus,
    f3PtpPTPPortPortIdentity                       PortIdentity,
    f3PtpPTPPortMaxExpectedL2Slaves                Unsigned32,
    f3PtpPTPPortMasterClockType                    MasterClockType,
    f3PtpPTPPortLastRcvdAnnounceMsg                F3DisplayString,
    f3PtpPTPPortLastRcvdSyncMsg                    F3DisplayString,
    f3PtpPTPPortLastRcvdDelayReqMsg                F3DisplayString,
    f3PtpPTPPortLastRcvdDelayRspMsg                F3DisplayString,
    f3PtpPTPPortMasterOnly                         TruthValue,
    f3PtpPTPPortIsProbingSlave                     TruthValue,
    f3PtpPTPPortPeerClockClass                     Unsigned32,
    f3PtpPTPPortMinimumExpectedClockClass          Integer32,
    f3PtpPTPPortDelayAsymmetryComp                 CompensationMode,
    f3PtpPTPPortAutoAsymmetryCompStatus            CompensationStatus,
    f3PtpPTPPortDelayAsymmetry                     Integer32,
    f3PtpPTPPortVirtualPortCtrl                    ToggleValue,
    f3PtpPTPPortDelayResponderType                 MasterClockType,
    f3PtpPTPPortTimeTraceable                      TruthValue,
    f3PtpPTPPortFrequencyTraceable                 TruthValue,
    f3PtpPTPPortDelayMechanism                     DelayMechanism,
    f3PtpPTPPortForcePRTCClockQuality              ToggleValue,
    f3PtpPTPPortScaledLogVariance                  Integer32,
    f3PtpPTPPortClockAccuracy                      Integer32,
    f3PtpPTPPortGMIdentity                         DisplayString,
    f3PtpPTPPortStepsRemoved                       Integer32,
    f3PtpPTPPortIfName                             DisplayString
}

f3PtpPTPPortIndex OBJECT-TYPE
    SYNTAX     Integer32
    MAX-ACCESS not-accessible 
    STATUS     current
    DESCRIPTION
         "Unique index value associated with the PTP Port Entity."
     ::= { f3PtpPTPPortEntry 1 }

f3PtpPTPPortAdminState OBJECT-TYPE
    SYNTAX      AdminState 
    MAX-ACCESS  read-write
    STATUS      current
    DESCRIPTION
          "This object represents the Administrative State of the PTP Port."
    ::= { f3PtpPTPPortEntry 2 }

f3PtpPTPPortAlias    OBJECT-TYPE
    SYNTAX      DisplayString (SIZE(0..256))
    MAX-ACCESS  read-write
    STATUS      current
    DESCRIPTION
         "This object allows SNMP management entities to provide an 
          alias to the PTP Port entity."
     ::= { f3PtpPTPPortEntry 3 }

f3PtpPTPPortOperationalState   OBJECT-TYPE
    SYNTAX      OperationalState 
    MAX-ACCESS  read-only
    STATUS      current
    DESCRIPTION
          "This object represents the Operational State of the PTP Port." 
    ::= { f3PtpPTPPortEntry 4 }

f3PtpPTPPortSecondaryState     OBJECT-TYPE
    SYNTAX      SecondaryState 
    MAX-ACCESS  read-only
    STATUS      current
    DESCRIPTION
           "This object represents the Secondary State of the PTP Port."
    ::= { f3PtpPTPPortEntry 5 }
                                 
f3PtpPTPPortPeerPortIdentity OBJECT-TYPE
    SYNTAX     PortIdentity 
    MAX-ACCESS read-only
    STATUS     current
    DESCRIPTION
         "This object specifies the Peer Port Identity of the PTP Port." 
     ::= { f3PtpPTPPortEntry 6 }
                                 
f3PtpPTPPortLocalPriority OBJECT-TYPE
    SYNTAX     Unsigned32 (1..255) 
    MAX-ACCESS read-write
    STATUS     current
    DESCRIPTION
        "This object allows configuration of  local priority used by the PTP Port." 
     ::= { f3PtpPTPPortEntry 7 }

f3PtpPTPPortPtpFlowPointEid OBJECT-TYPE
    SYNTAX     VariablePointer 
    MAX-ACCESS read-create
    STATUS     current
    DESCRIPTION
         "This object associates the PTP Flow Point Eid."
     ::= { f3PtpPTPPortEntry 8 }
                                 
f3PtpPTPPortNotSlave OBJECT-TYPE
    SYNTAX      TruthValue
    MAX-ACCESS  read-create
    STATUS      deprecated
    DESCRIPTION
           "This object indicate if PTP Port is slave."
    ::= { f3PtpPTPPortEntry 9 }

f3PtpPTPPortTxDestMacAddress OBJECT-TYPE
    SYNTAX     DestMacAddrType 
    MAX-ACCESS read-create
    STATUS     current
    DESCRIPTION
         "This object specifies the Mac address of the PTP Port." 
     ::= { f3PtpPTPPortEntry 10 }
                                 
f3PtpPTPPortSyncMessageRate OBJECT-TYPE
    SYNTAX     SyncMessageRate
    MAX-ACCESS read-create
    STATUS     current
    DESCRIPTION
        "This object allows specification of the PTP Port Sync 
         Message Rate." 
     ::= { f3PtpPTPPortEntry 11 }
                                 
f3PtpPTPPortmDelayReqRespMsgRate OBJECT-TYPE
    SYNTAX     DelayReqMessageRate
    MAX-ACCESS read-create
    STATUS     current
    DESCRIPTION
        "This object allows specification of the PTP Port Delay Response 
         Message Rate." 
     ::= { f3PtpPTPPortEntry 12 }
                                 
f3PtpPTPPortmAnnounceMsgRate OBJECT-TYPE
    SYNTAX     AnnounceMessageRate
    MAX-ACCESS read-create
    STATUS     current
    DESCRIPTION
         "This object allows specification of the PTP Port Announce Message Rate."
     ::= { f3PtpPTPPortEntry 13 }
                   
f3PtpPTPPortAnnounceReceiptTimeout OBJECT-TYPE
    SYNTAX     Integer32
    MAX-ACCESS read-write
    STATUS     current
    DESCRIPTION
        "This object allows specification of the PTP Port Announce Message 
         Receipt Timeout."
     ::= { f3PtpPTPPortEntry 14 }

f3PtpPTPPortSyncReceiptTimeout OBJECT-TYPE
    SYNTAX     Integer32
    MAX-ACCESS read-write
    STATUS     current
    DESCRIPTION
        "This object allows specification of the PTP Port Sync Message 
         Receipt Timeout."
     ::= { f3PtpPTPPortEntry 15 }

f3PtpPTPPortDelayRespTimeout OBJECT-TYPE
    SYNTAX     Integer32
    MAX-ACCESS read-write
    STATUS     current
    DESCRIPTION
        "This object allows specification of the PTP Port Delay Response 
         Message Receipt Timeout."
     ::= { f3PtpPTPPortEntry 16 }

f3PtpPTPPortPortState OBJECT-TYPE
    SYNTAX     PtpPortState 
    MAX-ACCESS read-only
    STATUS     current
    DESCRIPTION
         "This object provides the PTP Port state." 
     ::= { f3PtpPTPPortEntry 17 }
                          
f3PtpPTPPortBmcaDecisionCode OBJECT-TYPE
    SYNTAX     BMCARole 
    MAX-ACCESS read-only
    STATUS     current
    DESCRIPTION
         "This object provides the PTP Port BMCA Role" 
     ::= { f3PtpPTPPortEntry 18 }
                          
f3PtpPTPPortClockClass OBJECT-TYPE
    SYNTAX      Unsigned32
    MAX-ACCESS  read-only
    STATUS      current
    DESCRIPTION
           "This object specify PTP Port class."
     ::= { f3PtpPTPPortEntry 19 }
                          
f3PtpPTPPortPeerPortMacAddress OBJECT-TYPE
    SYNTAX      MacAddress 
    MAX-ACCESS  read-only
    STATUS      current
    DESCRIPTION
        "This attribute description PTP Port Mac Address."
    ::= { f3PtpPTPPortEntry 20 }

f3PtpPTPPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpPTPPortRowStatus supported are
            createAndGo(4) and destroy(6).  All mandatory attributes
            must be specified in a single SNMP SET request with
            f3PtpPTPPortRowStatus value as createAndGo(4).
            Upon successful row creation, this object has a
            value of active(1).

            The f3PtpPTPPortRowStatus object may be modified if
            the associated instance of this object is equal to active(1)."
    ::= { f3PtpPTPPortEntry 21 }
 
f3PtpPTPPortPortIdentity OBJECT-TYPE
   SYNTAX     PortIdentity 
   MAX-ACCESS read-only
   STATUS     current
   DESCRIPTION
        "This object specifies the Port Identity of the PTP Port." 
    ::= { f3PtpPTPPortEntry 22 }

f3PtpPTPPortMaxExpectedL2Slaves OBJECT-TYPE
    SYNTAX     Unsigned32 
    MAX-ACCESS read-create
    STATUS     current
    DESCRIPTION
         "This object specifies the max number of l2 slaves of the PTP Port." 
     ::= { f3PtpPTPPortEntry 23 }

f3PtpPTPPortMasterClockType    OBJECT-TYPE
    SYNTAX      MasterClockType 
    MAX-ACCESS  read-create
    STATUS     current
    DESCRIPTION
          "This object allows specification of the Master Clock Type of the 
           PTP Port." 
    ::= { f3PtpPTPPortEntry 24 }

f3PtpPTPPortLastRcvdAnnounceMsg OBJECT-TYPE
   SYNTAX     F3DisplayString 
   MAX-ACCESS read-only
   STATUS     current
   DESCRIPTION
        "This object specifies the last recieved announce message." 
    ::= { f3PtpPTPPortEntry 25 }
 
f3PtpPTPPortLastRcvdSyncMsg OBJECT-TYPE
   SYNTAX     F3DisplayString 
   MAX-ACCESS read-only
   STATUS     current
   DESCRIPTION
        "This object specifies the last recieved sync message." 
    ::= { f3PtpPTPPortEntry 26 }
 
f3PtpPTPPortLastRcvdDelayReqMsg OBJECT-TYPE
   SYNTAX     F3DisplayString 
   MAX-ACCESS read-only
   STATUS     current
   DESCRIPTION
        "This object specifies the last recieved delay request message." 
    ::= { f3PtpPTPPortEntry 27 }
 
f3PtpPTPPortLastRcvdDelayRspMsg OBJECT-TYPE
   SYNTAX     F3DisplayString 
   MAX-ACCESS read-only
   STATUS     current
   DESCRIPTION
        "This object specifies the last recieved response message." 
    ::= { f3PtpPTPPortEntry 28 }
    
f3PtpPTPPortMasterOnly OBJECT-TYPE
    SYNTAX      TruthValue
    MAX-ACCESS  read-create
    STATUS      current
    DESCRIPTION
           "This object indicate if PTP Port is master only."
    ::= { f3PtpPTPPortEntry 29 }
    
f3PtpPTPPortIsProbingSlave OBJECT-TYPE
    SYNTAX      TruthValue
    MAX-ACCESS  read-create
    STATUS      current
    DESCRIPTION
           "This object indicate if PTP Port is probing slave."
    ::= { f3PtpPTPPortEntry 30 }

f3PtpPTPPortPeerClockClass OBJECT-TYPE
    SYNTAX      Unsigned32
    MAX-ACCESS  read-only
    STATUS      current
    DESCRIPTION
           "This object specify PTP Port peer clock class."
     ::= { f3PtpPTPPortEntry 31 }


f3PtpPTPPortMinimumExpectedClockClass OBJECT-TYPE
    SYNTAX     Integer32 (0..255)
    MAX-ACCESS read-write
    STATUS     current
    DESCRIPTION
        "Note: This value is only applicable for a dynamic or slave port that is 
     related to a PTP clock, either a boundary clock or slave clock. 
     Otherwise, this field is not applicable (N/A) and cannot be configured.  

     This object allows setting the minimum expected clock class value,
     which setes the minimum threshold for receiving packets.
     if the received clock clock class is greater than the expected
     clock class value, the packets for the grandmaster or boundary clock that
     are sending this clock class are dropped.
     In addition, an alarm called clock-class-mismatch is generated. The default is 247."
     ::= { f3PtpPTPPortEntry 32 }

f3PtpPTPPortDelayAsymmetryComp OBJECT-TYPE
    SYNTAX     CompensationMode
    MAX-ACCESS read-write
    STATUS     current
    DESCRIPTION
        "This object allows configuration of asymmetry delay
        compensation mode for L2 PTP slave on OSA540X."   
     ::= { f3PtpPTPPortEntry 33 }

f3PtpPTPPortAutoAsymmetryCompStatus OBJECT-TYPE
    SYNTAX     CompensationStatus  
    MAX-ACCESS read-only
    STATUS     current
    DESCRIPTION
        "This object provides the automatic delay asymmetry 
        compensation status for L2 PTP slave on OSA540X." 
     ::= { f3PtpPTPPortEntry 34 }

f3PtpPTPPortDelayAsymmetry OBJECT-TYPE
    SYNTAX     Integer32 
    MAX-ACCESS read-write
    STATUS     current
    DESCRIPTION
        "This object is used for manual configuration of delay asymmetry
        in ns if delay asymmetry compensation is Manual.
        Or for indication of the measured delay asymmetry if
        delay asymmetry compensation is automatic."
     ::= { f3PtpPTPPortEntry 35 }

f3PtpPTPPortVirtualPortCtrl OBJECT-TYPE                    
    SYNTAX      ToggleValue
    MAX-ACCESS  read-create
    STATUS      current
    DESCRIPTION
           "This object indicate if PTP Port is virtual."
    ::= { f3PtpPTPPortEntry 36 }
    
f3PtpPTPPortDelayResponderType    OBJECT-TYPE
    SYNTAX      MasterClockType 
    MAX-ACCESS  read-create
    STATUS     current
    DESCRIPTION
          "This object allows specification of the Delay Responder Type for the 
           PTP Port." 
    ::= { f3PtpPTPPortEntry 37 }

f3PtpPTPPortTimeTraceable    OBJECT-TYPE
    SYNTAX      TruthValue 
    MAX-ACCESS  read-only
    STATUS     current
    DESCRIPTION
          "This object indicates the Time Traceable for the 
           PTP Port." 
    ::= { f3PtpPTPPortEntry 38 }

f3PtpPTPPortFrequencyTraceable    OBJECT-TYPE
    SYNTAX      TruthValue 
    MAX-ACCESS  read-only
    STATUS     current
    DESCRIPTION
          "This object indicates the Frequency Traceable for the 
           PTP Port." 
    ::= { f3PtpPTPPortEntry 39 }
    
f3PtpPTPPortDelayMechanism    OBJECT-TYPE
    SYNTAX      DelayMechanism
    MAX-ACCESS  read-write
    STATUS     current
    DESCRIPTION
          "This object is used for manual configuration of Delay Mechanism,
          which can be one-way or two-way" 
    ::= { f3PtpPTPPortEntry 40 }
    
f3PtpPTPPortForcePRTCClockQuality OBJECT-TYPE                    
    SYNTAX      ToggleValue
    MAX-ACCESS  read-write
    STATUS      current
    DESCRIPTION
           "This object indicate is used to force PRTC attributes when time clock 
           is configured to EPRTC mode."
    ::= { f3PtpPTPPortEntry 41 }

f3PtpPTPPortScaledLogVariance OBJECT-TYPE
    SYNTAX     Integer32 
    MAX-ACCESS read-only
    STATUS     current
    DESCRIPTION
         "This object indicates the Offset Scaled Log Variance of the clock that contains the port"
     ::= { f3PtpPTPPortEntry 42 }

f3PtpPTPPortClockAccuracy OBJECT-TYPE
    SYNTAX     Integer32 
    MAX-ACCESS read-only
    STATUS     current
    DESCRIPTION
         "This object indicates the Clock Accuracy of the clock that contains the port"
     ::= { f3PtpPTPPortEntry 43 }

f3PtpPTPPortGMIdentity OBJECT-TYPE
    SYNTAX     DisplayString (SIZE(0..16))
    MAX-ACCESS read-only
    STATUS     current
    DESCRIPTION
         "This object indicates the Grandmaster Identity of the clock that contains the port"
     ::= { f3PtpPTPPortEntry 44 }

f3PtpPTPPortStepsRemoved OBJECT-TYPE
    SYNTAX     Integer32 
    MAX-ACCESS read-only
    STATUS     current
    DESCRIPTION
         "This object indicates the number of Steps Removed for the port"
     ::= { f3PtpPTPPortEntry 45 }
         
f3PtpPTPPortIfName OBJECT-TYPE
    SYNTAX         DisplayString (SIZE(0..15))
    MAX-ACCESS     read-create
    STATUS         current
    DESCRIPTION
         "This object allows SNMP management entities to provide a
          name to the PTP Port IP interface."
     ::= { f3PtpPTPPortEntry 46 }


--- NOTE: To support IEEE 1588 Default Profile L2
f3PtpL2DynamicRemoteSlaveTable OBJECT-TYPE
       SYNTAX     SEQUENCE OF F3PtpL2DynamicRemoteSlaveEntry
       MAX-ACCESS not-accessible
       STATUS     current
       DESCRIPTION
           "A list of entries corresponding L2 dynamic remote slaves."
    ::= { f3PtpConfigObjects 21 }


f3PtpL2DynamicRemoteSlaveEntry OBJECT-TYPE
       SYNTAX     F3PtpL2DynamicRemoteSlaveEntry
       MAX-ACCESS not-accessible
       STATUS     current
       DESCRIPTION
             "An entry containing information applicable to a particular
             L2 Dynamic Remote Slave entity."
       INDEX { neIndex, f3PtpPTPClockIndex, f3PtpPTPPortIndex, f3PtpL2DynamicRemoteSlaveIndex }
       ::= { f3PtpL2DynamicRemoteSlaveTable 1 }

F3PtpL2DynamicRemoteSlaveEntry ::= SEQUENCE {
     f3PtpL2DynamicRemoteSlaveIndex              Integer32,
     f3PtpL2DynamicRemoteSlavePortIdentity       PortIdentity,
     f3PtpL2DynamicRemoteSlaveMacAddress         MacAddress,
     f3PtpL2DynamicRemoteSlaveRowStatus          RowStatus,
     f3PtpL2DynamicRemoteSlaveStorageType        StorageType,
     f3PtpL2DynamicRemoteSlaveClockIdentity      ClockIdentity
  }

f3PtpL2DynamicRemoteSlaveIndex OBJECT-TYPE
    SYNTAX     Integer32
    MAX-ACCESS not-accessible 
    STATUS     current
    DESCRIPTION
         "Unique index value associated with the Remote Slave."
     ::= { f3PtpL2DynamicRemoteSlaveEntry 1 }

f3PtpL2DynamicRemoteSlavePortIdentity OBJECT-TYPE
    SYNTAX     PortIdentity 
    MAX-ACCESS read-only
    STATUS     current
    DESCRIPTION
         "This object represents the Port Identity of the L2 Remote Slave."
     ::= { f3PtpL2DynamicRemoteSlaveEntry 2 }

f3PtpL2DynamicRemoteSlaveMacAddress OBJECT-TYPE
    SYNTAX     MacAddress
    MAX-ACCESS read-only 
    STATUS     current
    DESCRIPTION
         "This object allows specification of the Mac Address of
          the L2 Remote Slave."
     ::= { f3PtpL2DynamicRemoteSlaveEntry 3 }


f3PtpL2DynamicRemoteSlaveRowStatus OBJECT-TYPE
    SYNTAX     RowStatus
    MAX-ACCESS read-create
    STATUS     current
    DESCRIPTION
           "The status of this row.  An entry MUST NOT exist in the 
            active state unless all objects in the entry have an 
            appropriate value, as described
            in the description clause for each writable object.

            The values of f3PtpL2DynamicRemoteSlaveRowStatus supported is
            destroy(6).  

            The f3PtpL2DynamicRemoteSlaveRowStatus object may be modified if
            the associated instance of this object is equal to active(1)."
    ::= { f3PtpL2DynamicRemoteSlaveEntry 4 }


f3PtpL2DynamicRemoteSlaveStorageType OBJECT-TYPE
    SYNTAX     StorageType
    MAX-ACCESS read-create
    STATUS     current
    DESCRIPTION
            "The type of storage configured for this entry."
    ::= { f3PtpL2DynamicRemoteSlaveEntry 5 }



f3PtpL2DynamicRemoteSlaveClockIdentity OBJECT-TYPE
    SYNTAX     ClockIdentity
    MAX-ACCESS read-only 
    STATUS     current
    DESCRIPTION
         "L2 Dynamic Remote Slave Clock Identity for this entry."
     ::= { f3PtpL2DynamicRemoteSlaveEntry 6 }

--
-- PTP MCI Protection Group Table 
--
f3PtpMCIProtGroupTable OBJECT-TYPE
    SYNTAX     SEQUENCE OF F3PtpMCIProtGroupEntry
    MAX-ACCESS not-accessible
    STATUS     current
    DESCRIPTION
            "A list of entries corresponding to the MCI Protection Groups.
             "
    ::= { f3PtpConfigObjects 22 }

f3PtpMCIProtGroupEntry OBJECT-TYPE
    SYNTAX     F3PtpMCIProtGroupEntry
    MAX-ACCESS not-accessible
    STATUS     current
    DESCRIPTION
            "An entry containing information applicable to a PTP MCI
             Protection Group."
    INDEX { neIndex, f3PtpMCIProtGroupIndex }
    ::= { f3PtpMCIProtGroupTable 1 }

F3PtpMCIProtGroupEntry ::= SEQUENCE {
    f3PtpMCIProtGroupIndex                    Integer32,
    f3PtpMCIProtGroupAdminState               AdminState,
    f3PtpMCIProtGroupActiveMember             VariablePointer,
    f3PtpMCIProtGroupLastSwitchOverTime       TimeTicks,
    f3PtpMCIProtGroupLastSwitchOverReason     CmGenPgSwitchoverReason,
    f3PtpMCIProtGroupStorageType              StorageType, 
    f3PtpMCIProtGroupRowStatus                RowStatus,
    f3PtpMCIProtGroupPriority                 CmProtGropEntPrio
}

f3PtpMCIProtGroupIndex OBJECT-TYPE
    SYNTAX     Integer32
    MAX-ACCESS read-only 
    STATUS     current
    DESCRIPTION
         "Unique index value associated with the PTP MCI Protection Group
          entity."
     ::= { f3PtpMCIProtGroupEntry 1 }

f3PtpMCIProtGroupAdminState OBJECT-TYPE
    SYNTAX         AdminState
    MAX-ACCESS     read-write
    STATUS         current
    DESCRIPTION
         "This object represents the Administrative State of the PTP MCI
          Protection Group."
    ::= { f3PtpMCIProtGroupEntry 2 }

f3PtpMCIProtGroupActiveMember OBJECT-TYPE
    SYNTAX     VariablePointer
    MAX-ACCESS read-only 
    STATUS     current
    DESCRIPTION
         "The corresponding OID of the Active Member in the PTP MCI Protection Group."
     ::= { f3PtpMCIProtGroupEntry 3 }
     
f3PtpMCIProtGroupLastSwitchOverTime OBJECT-TYPE
    SYNTAX     TimeTicks
    MAX-ACCESS read-only 
    STATUS     current
    DESCRIPTION
         "The value of sysUpTime when last switch over occurred."
     ::= { f3PtpMCIProtGroupEntry 4 }

f3PtpMCIProtGroupLastSwitchOverReason OBJECT-TYPE
    SYNTAX     CmGenPgSwitchoverReason
    MAX-ACCESS read-only 
    STATUS     current
    DESCRIPTION
         "The reason for last switch over in the PTP MCI Protection Group."
     ::= { f3PtpMCIProtGroupEntry 5 }

f3PtpMCIProtGroupStorageType OBJECT-TYPE
    SYNTAX     StorageType
    MAX-ACCESS read-create
    STATUS     current
    DESCRIPTION
            "The type of storage configured for this entry."
    ::= { f3PtpMCIProtGroupEntry 6 }

f3PtpMCIProtGroupRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMCIProtGroupRowStatus supported are
            createAndGo(4) and destroy(6).  All mandatory attributes
            must be specified in a single SNMP SET request with
            f3PtpMCIProtGroupRowStatus value as createAndGo(4).
            Upon successful row creation, this object has a
            value of active(1).

            The f3PtpMCIProtGroupRowStatus object may be modified if
            the associated instance of this object is equal to active(1)."
    ::= { f3PtpMCIProtGroupEntry 7 }

f3PtpMCIProtGroupPriority OBJECT-TYPE
    SYNTAX CmProtGropEntPrio     
    MAX-ACCESS read-write 
    STATUS     current
    DESCRIPTION
         "The priority value for this group."
     ::= { f3PtpMCIProtGroupEntry 8 }

---
--- Ptp MCI Protection Member Table
---
f3PtpMCIProtMemberTable  OBJECT-TYPE
    SYNTAX      SEQUENCE OF F3PtpMCIProtMemberEntry
    MAX-ACCESS  not-accessible
    STATUS      current
    DESCRIPTION
            "A list of entries for the Ptp MCI Protection Group Members."
    ::= { f3PtpConfigObjects 23 }

f3PtpMCIProtMemberEntry  OBJECT-TYPE
    SYNTAX      F3PtpMCIProtMemberEntry
    MAX-ACCESS  not-accessible
    STATUS      current
    DESCRIPTION
            "A conceptual row in the f3PtpMCIProtMemberTable."
    INDEX { neIndex, f3PtpMCIProtGroupIndex, f3PtpMCIProtMemberObject }
    ::= { f3PtpMCIProtMemberTable 1 }

F3PtpMCIProtMemberEntry ::= SEQUENCE {
    f3PtpMCIProtMemberObject             VariablePointer,
    f3PtpMCIProtMemberStorageType        StorageType,
    f3PtpMCIProtMemberRowStatus          RowStatus
}

f3PtpMCIProtMemberObject OBJECT-TYPE
    SYNTAX      VariablePointer
    MAX-ACCESS  not-accessible
    STATUS      current
    DESCRIPTION
           "This object points to the Protection Group Member."
    ::= { f3PtpMCIProtMemberEntry 1 }

f3PtpMCIProtMemberStorageType OBJECT-TYPE
    SYNTAX      StorageType
    MAX-ACCESS  read-create
    STATUS      current
    DESCRIPTION
           "The type of storage configured for this entry."
    ::= { f3PtpMCIProtMemberEntry 2 }

f3PtpMCIProtMemberRowStatus OBJECT-TYPE
    SYNTAX      RowStatus
    MAX-ACCESS  read-create
    STATUS      current
    DESCRIPTION
           "The status of this row.
            An entry MUST NOT exist in the active state unless all
            objects in the entry have an appropriate value, as described
            in the description clause for each writable object.
    
            The values of f3PtpMCIProtMemberRowStatus supported are
            createAndGo(4) and destroy(6).  All mandatory attributes
            must be specified in a single SNMP SET request with
            f3PtpMCIProtMemberRowStatus value as createAndGo(4).
            Upon successful row creation, this object has a
            value of active(1).
    
            The f3PtpMCIProtMemberRowStatus object may be modified if
            the associated instance of this object is equal to active(1)."
    ::= { f3PtpMCIProtMemberEntry 3 }

--
-- Traffic Port FlowPoint Extension Table
--
f3PtpTrafficPortFlowPointExtTable  OBJECT-TYPE
    SYNTAX      SEQUENCE OF F3PtpTrafficPortFlowPointExtEntry
    MAX-ACCESS  not-accessible
    STATUS      current
    DESCRIPTION
            "This table extends f3PtpTrafficPortFlowPointTable."
    ::= { f3PtpConfigObjects 24 }

f3PtpTrafficPortFlowPointExtEntry OBJECT-TYPE
    SYNTAX      F3PtpTrafficPortFlowPointExtEntry
    MAX-ACCESS  not-accessible
    STATUS      current
    DESCRIPTION
            "A conceptual row in the f3PtpTrafficPortFlowPointExtTable."
    AUGMENTS { f3PtpTrafficPortFlowPointEntry }
    ::= { f3PtpTrafficPortFlowPointExtTable 1 }

F3PtpTrafficPortFlowPointExtEntry ::= SEQUENCE {
    f3PtpTrafficPortFlowPointBufferSize Integer32
}

f3PtpTrafficPortFlowPointBufferSize OBJECT-TYPE
     SYNTAX     Integer32
     MAX-ACCESS read-write
     STATUS     current
     DESCRIPTION
         "This object allows configuring the buffer size for the
         PTP FlowPoint's bandwidth profile. The default value is 16KB."
     ::= { f3PtpTrafficPortFlowPointExtEntry 1 }

--
-- L3 PTP Port Table      
--
f3PtpL3PTPPortTable OBJECT-TYPE
    SYNTAX     SEQUENCE OF F3PtpL3PTPPortEntry
    MAX-ACCESS not-accessible
    STATUS     current
    DESCRIPTION
       "A list of entries corresponding to the L3 PTP Port entities."
    ::= { f3PtpConfigObjects 25 }

f3PtpL3PTPPortEntry OBJECT-TYPE
    SYNTAX     F3PtpL3PTPPortEntry
    MAX-ACCESS not-accessible
    STATUS     current
    DESCRIPTION
          "An entry containing information applicable to a particular
           L3 PTP Port Entity."
    INDEX { neIndex, f3PtpPTPClockIndex,f3PtpL3PTPPortIndex}
            
    ::= { f3PtpL3PTPPortTable 1 }


F3PtpL3PTPPortEntry ::= SEQUENCE {
    f3PtpL3PTPPortIndex                              Integer32,
    f3PtpL3PTPPortAdminState                         AdminState,
    f3PtpL3PTPPortAlias                              DisplayString,          
    f3PtpL3PTPPortOperationalState                   OperationalState,  
    f3PtpL3PTPPortSecondaryState                     SecondaryState,
    f3PtpL3PTPPortPortIdentity                       PortIdentity,    
    f3PtpL3PTPPortLocalPriority                      Unsigned32,         
    f3PtpL3PTPPortPtpFlowPointEid                    VariablePointer,         
    f3PtpL3PTPPortSyncMessageRate                    SyncMessageRate,   
    f3PtpL3PTPPortDelayReqRespMsgRate                DelayReqMessageRate,
    f3PtpL3PTPPortAnnounceMsgRate                    AnnounceMessageRate,
    f3PtpL3PTPPortAnnounceReceiptTimeout             Integer32,                            
    f3PtpL3PTPPortSyncReceiptTimeout                 Integer32,                            
    f3PtpL3PTPPortDelayRespTimeout                   Integer32,  
    f3PtpL3PTPPortPortState                          PtpPortState,
    f3PtpL3PTPPortBmcaDecisionCode                   BMCARole, 
    f3PtpL3PTPPortPeerClockClass                     Unsigned32, 
    f3PtpL3PTPPortMinimumExpectedClockClass          Integer32,
    f3PtpL3PTPPortIpProtocol                         IpVersion,
    f3PtpL3PTPPortIfName                             DisplayString,
    f3PtpL3PTPPortIpPriorityMapMode                  IpPriorityMapMode,
    f3PtpL3PTPPortIpPriority                         Integer32,
    f3PtpL3PTPPortIpV4Address                        IpAddress,
    f3PtpL3PTPPortIpV4SubnetMask                     IpAddress,
    f3PtpL3PTPPortIpV6Address                        Ipv6Address,             
    f3PtpL3PTPPortIpV6AddrPrefixLength               Integer32,
    f3PtpL3PTPPortDefaultGatewayControl              ToggleValue,
    f3PtpL3PTPPortGateway                            IpAddress,
    f3PtpL3PTPPortIpV6Gateway                        Ipv6Address,
    f3PtpL3PTPPortUnicastMessageNegEnabled           TruthValue,
    f3PtpL3PTPPortTransmitDuration                   Integer32,
    f3PtpL3PTPPortRequestUnicastTimeout              Integer32,
    f3PtpL3PTPPortRequestUnicastRestartTimer         Integer32,
    f3PtpL3PTPPortMasterIpV4Address                  IpAddress,
    f3PtpL3PTPPortMasterIpV6Address                  Ipv6Address,
    f3PtpL3PTPPortDelayAsymmetryComp                 CompensationMode,
    f3PtpL3PTPPortAutoAsymmetryCompStatus            CompensationStatus,
    f3PtpL3PTPPortDelayAsymmetry                     Integer32,
    f3PtpL3PTPPortStorageType                        StorageType,
    f3PtpL3PTPPortRowStatus                          RowStatus,
    f3PtpL3PTPPortDelayReqDestIpAddrType             PTPTransportMode,
    f3PtpL3PTPPortScaledLogVariance                  Integer32,
    f3PtpL3PTPPortClockAccuracy                      Integer32,
    f3PtpL3PTPPortGMIdentity                         DisplayString,
    f3PtpL3PTPPortStepsRemoved                       Integer32,
    f3PtpL3PTPPortVirtualPortCtrl                    ToggleValue,
    f3PtpL3PTPPortLastRcvdAnnounceMsg                F3DisplayString,
    f3PtpL3PTPPortLastRcvdSyncMsg                    F3DisplayString,
    f3PtpL3PTPPortLastRcvdDelayReqMsg                F3DisplayString,
    f3PtpL3PTPPortLastRcvdDelayRspMsg                F3DisplayString,
    f3PtpL3PTPPortMaxLeaseDuration                   Integer32,
    f3PtpL3PTPPortMaxSlavesSupported                 Integer32,
    f3PtpL3PTPPortMaxAnnounceMessageRate             AnnounceMsgRate,
    f3PtpL3PTPPortMaxSyncMessageRate                 SyncMsgRate,
    f3PtpL3PTPPortMaxDelayRespMessageRate            DelayRespMsgRate,
    f3PtpL3PTPPortMasterOnly                         TruthValue
}

f3PtpL3PTPPortIndex OBJECT-TYPE
    SYNTAX     Integer32
    MAX-ACCESS not-accessible 
    STATUS     current
    DESCRIPTION
         "Unique index value associated with the L3 PTP Port Entity."
     ::= { f3PtpL3PTPPortEntry 1 }

f3PtpL3PTPPortAdminState OBJECT-TYPE
    SYNTAX      AdminState 
    MAX-ACCESS  read-write
    STATUS      current
    DESCRIPTION
          "This object represents the Administrative State of the L3 PTP Port."
    ::= { f3PtpL3PTPPortEntry 2 }

f3PtpL3PTPPortAlias    OBJECT-TYPE
    SYNTAX      DisplayString (SIZE(0..256))
    MAX-ACCESS  read-write
    STATUS      current
    DESCRIPTION
         "This object allows SNMP management entities to provide an 
          alias to the L3 PTP Port entity."
     ::= { f3PtpL3PTPPortEntry 3 }

f3PtpL3PTPPortOperationalState   OBJECT-TYPE
    SYNTAX      OperationalState 
    MAX-ACCESS  read-only
    STATUS      current
    DESCRIPTION
          "This object represents the Operational State of the L3 PTP Port." 
    ::= { f3PtpL3PTPPortEntry 4 }

f3PtpL3PTPPortSecondaryState     OBJECT-TYPE
    SYNTAX      SecondaryState 
    MAX-ACCESS  read-only
    STATUS      current
    DESCRIPTION
           "This object represents the Secondary State of the L3 PTP Port."
    ::= { f3PtpL3PTPPortEntry 5 }
                                 
f3PtpL3PTPPortPortIdentity OBJECT-TYPE
   SYNTAX     PortIdentity 
   MAX-ACCESS read-only
   STATUS     current
   DESCRIPTION
        "This object specifies the Port Identity of the L3 PTP Port." 
    ::= { f3PtpL3PTPPortEntry 6 }                                                                
                                 
f3PtpL3PTPPortLocalPriority OBJECT-TYPE
    SYNTAX     Unsigned32 (1..255) 
    MAX-ACCESS read-write
    STATUS     current
    DESCRIPTION
        "This object allows configuration of  local priority used by the L3 PTP Port." 
     ::= { f3PtpL3PTPPortEntry 7 }

f3PtpL3PTPPortPtpFlowPointEid OBJECT-TYPE
    SYNTAX     VariablePointer 
    MAX-ACCESS read-create
    STATUS     current
    DESCRIPTION
         "This object associates the PTP Flow Point Eid."
     ::= { f3PtpL3PTPPortEntry 8 }
                                 
                                 
f3PtpL3PTPPortSyncMessageRate OBJECT-TYPE
    SYNTAX     SyncMessageRate
    MAX-ACCESS read-create
    STATUS     current
    DESCRIPTION
        "This object allows specification of the L3 PTP Port Sync 
         Message Rate." 
     ::= { f3PtpL3PTPPortEntry 9 }
                                 
f3PtpL3PTPPortDelayReqRespMsgRate OBJECT-TYPE
    SYNTAX     DelayReqMessageRate
    MAX-ACCESS read-create
    STATUS     current
    DESCRIPTION
        "This object allows specification of the L3 PTP Port Delay Response 
         Message Rate." 
     ::= { f3PtpL3PTPPortEntry 10 }
                                 
f3PtpL3PTPPortAnnounceMsgRate OBJECT-TYPE
    SYNTAX     AnnounceMessageRate
    MAX-ACCESS read-create
    STATUS     current
    DESCRIPTION
         "This object allows specification of the L3 PTP Port Announce Message Rate."
     ::= { f3PtpL3PTPPortEntry 11 }
                   
f3PtpL3PTPPortAnnounceReceiptTimeout OBJECT-TYPE
    SYNTAX     Integer32 (2..255)
    MAX-ACCESS read-write
    STATUS     current
    DESCRIPTION
        "This object allows specification of the L3 PTP Port Announce Message 
         Receipt Timeout."
     ::= { f3PtpL3PTPPortEntry 12 }

f3PtpL3PTPPortSyncReceiptTimeout OBJECT-TYPE
    SYNTAX     Integer32 (2..128)
    MAX-ACCESS read-write
    STATUS     current
    DESCRIPTION
        "This object allows specification of the L3 PTP Port Sync Message 
         Receipt Timeout."
     ::= { f3PtpL3PTPPortEntry 13 }

f3PtpL3PTPPortDelayRespTimeout OBJECT-TYPE
    SYNTAX     Integer32 (2..128)
    MAX-ACCESS read-write
    STATUS     current
    DESCRIPTION
        "This object allows specification of the L3 PTP Port Delay Response 
         Message Receipt Timeout."
     ::= { f3PtpL3PTPPortEntry 14 }

f3PtpL3PTPPortPortState OBJECT-TYPE
    SYNTAX     PtpPortState 
    MAX-ACCESS read-only
    STATUS     current
    DESCRIPTION
         "This object provides the L3 PTP Port state." 
     ::= { f3PtpL3PTPPortEntry 15 }
                          
f3PtpL3PTPPortBmcaDecisionCode OBJECT-TYPE
    SYNTAX     BMCARole 
    MAX-ACCESS read-only
    STATUS     current
    DESCRIPTION
         "This object provides the L3 PTP Port BMCA Role" 
     ::= { f3PtpL3PTPPortEntry 16 }
                          
f3PtpL3PTPPortPeerClockClass OBJECT-TYPE
    SYNTAX      Unsigned32
    MAX-ACCESS  read-only
    STATUS      current
    DESCRIPTION
           "This object specify L3 PTP Port class."
     ::= { f3PtpL3PTPPortEntry 17 }
     
f3PtpL3PTPPortMinimumExpectedClockClass OBJECT-TYPE
    SYNTAX     Integer32 (0..255)
    MAX-ACCESS read-write
    STATUS     current
    DESCRIPTION
        "Note: This value is only applicable for a dynamic or slave port that is 
     related to a PTP clock, either a boundary clock or slave clock. 
     Otherwise, this field is not applicable (N/A) and cannot be configured.  

     This object allows setting the minimum expected clock class value,
     which setes the minimum threshold for receiving packets.
     if the received clock clock class is greater than the expected
     clock class value, the packets for the grandmaster or boundary clock that
     are sending this clock class are dropped.
     In addition, an alarm called clock-class-mismatch is generated. The default is 247."
     ::= { f3PtpL3PTPPortEntry 18 }                          
 
f3PtpL3PTPPortIpProtocol OBJECT-TYPE
    SYNTAX     IpVersion
    MAX-ACCESS read-create 
    STATUS     current
    DESCRIPTION
         "This object allows specification of the IP Protocol of the L3 PTP Port."
     ::= { f3PtpL3PTPPortEntry 19 }

f3PtpL3PTPPortIfName     OBJECT-TYPE
    SYNTAX         DisplayString (SIZE(0..15))
    MAX-ACCESS     read-create
    STATUS         current
    DESCRIPTION
         "This object allows SNMP management entities to provide a
          name to the L3 PTP Port IP interface."
     ::= { f3PtpL3PTPPortEntry 20 }

f3PtpL3PTPPortIpPriorityMapMode  OBJECT-TYPE
    SYNTAX     IpPriorityMapMode 
    MAX-ACCESS read-create
    STATUS     current
    DESCRIPTION
         "This object enables specification of Priority Mapping Mode for
          the  L3 PTP Port IP interface."
     ::= { f3PtpL3PTPPortEntry 21 }

f3PtpL3PTPPortIpPriority  OBJECT-TYPE
    SYNTAX     Integer32 (0..63)
    MAX-ACCESS read-create
    STATUS     current
    DESCRIPTION
         "This object enables specification of Priority Value for the
          L3 PTP Port IP interface."
     ::= { f3PtpL3PTPPortEntry 22 }

f3PtpL3PTPPortIpV4Address OBJECT-TYPE
    SYNTAX     IpAddress
    MAX-ACCESS read-create 
    STATUS     current
    DESCRIPTION
         "This object allows specification of the IPv4 Address of
          the L3 PTP Port IP interface."
     ::= { f3PtpL3PTPPortEntry 23 }

f3PtpL3PTPPortIpV4SubnetMask OBJECT-TYPE
    SYNTAX     IpAddress
    MAX-ACCESS read-create 
    STATUS     current
    DESCRIPTION
         "This object allows specification of the IPv4 Subnet Mask of
          the L3 PTP Port IP interface."
     ::= { f3PtpL3PTPPortEntry 24 }

f3PtpL3PTPPortIpV6Address OBJECT-TYPE
    SYNTAX     Ipv6Address 
    MAX-ACCESS read-create
    STATUS   current
    DESCRIPTION
         "This object allows specification of the unicast ipv6 Address of
          the L3 PTP Port IP interface."
    ::= { f3PtpL3PTPPortEntry 25 }

f3PtpL3PTPPortIpV6AddrPrefixLength OBJECT-TYPE
    SYNTAX     Integer32 
    MAX-ACCESS read-create
    STATUS   current
    DESCRIPTION
         "This object allows specification of the unicast IPv6 address prefix length of
          the L3 PTP Port IP interface."
    ::= { f3PtpL3PTPPortEntry 26 }


f3PtpL3PTPPortDefaultGatewayControl OBJECT-TYPE
    SYNTAX     ToggleValue
    MAX-ACCESS read-create
    STATUS     current
    DESCRIPTION
         "This attribute control Gateway address for the L3 PTP Port IP interface."
     ::= { f3PtpL3PTPPortEntry 27 }

f3PtpL3PTPPortGateway OBJECT-TYPE
    SYNTAX     IpAddress
    MAX-ACCESS read-create 
    STATUS     current
    DESCRIPTION
         "This object allows specification of the IPv4 Gateway Address of
          the L3 PTP Port IP interface."
     ::= { f3PtpL3PTPPortEntry 28 }

f3PtpL3PTPPortIpV6Gateway OBJECT-TYPE
    SYNTAX     Ipv6Address 
    MAX-ACCESS read-create
    STATUS   current
    DESCRIPTION
         "This object allows specification of the IPv6 Gateway Address of
          the L3 PTP Port IP interface."
    ::= { f3PtpL3PTPPortEntry 29 }

f3PtpL3PTPPortUnicastMessageNegEnabled OBJECT-TYPE
    SYNTAX     TruthValue
    MAX-ACCESS read-create 
    STATUS     current
    DESCRIPTION
         "This object must be used to specify whether Unicast Message
          Negotiation is enabled for the L3 PTP Port."
     ::= { f3PtpL3PTPPortEntry 30 }

f3PtpL3PTPPortTransmitDuration  OBJECT-TYPE 
    SYNTAX     Integer32 (60..1000)
    MAX-ACCESS read-write
    STATUS     current
    DESCRIPTION
        "This object specifices Duration Field in the REQUEST_UNICAST_TRANSMISSION_TLV."
     ::= { f3PtpL3PTPPortEntry 31 }

f3PtpL3PTPPortRequestUnicastTimeout  OBJECT-TYPE 
    SYNTAX     Integer32 (1..600)
    MAX-ACCESS read-write
    STATUS     current
    DESCRIPTION
        "This object allows specification of the Request Unicast 
         Timeout in seconds.  Unicast transmission is termed as
         failed when this timeout occurs."
     ::= { f3PtpL3PTPPortEntry 32 }

f3PtpL3PTPPortRequestUnicastRestartTimer  OBJECT-TYPE 
    SYNTAX     Integer32 (30..1800)
    MAX-ACCESS read-write
    STATUS     current
    DESCRIPTION
        "This object allows specification of the time (in seconds) to wait
         to restart the Request Unicast signalling." 
     ::= { f3PtpL3PTPPortEntry 33 }

f3PtpL3PTPPortMasterIpV4Address OBJECT-TYPE
    SYNTAX     IpAddress
    MAX-ACCESS read-create 
    STATUS     current
    DESCRIPTION
         "This object allows specification of the IPv4 Address of
          the PTP Master."
     ::= { f3PtpL3PTPPortEntry 34 }

f3PtpL3PTPPortMasterIpV6Address OBJECT-TYPE
    SYNTAX     Ipv6Address 
    MAX-ACCESS read-create
    STATUS   current
    DESCRIPTION
         "This object allows specification of the unicast ipv6 Address of
          the PTP Master."
    ::= { f3PtpL3PTPPortEntry 35 }

f3PtpL3PTPPortDelayAsymmetryComp OBJECT-TYPE
    SYNTAX     CompensationMode
    MAX-ACCESS read-write
    STATUS     current
    DESCRIPTION
        "This object allows configuration of asymmetry delay
        compensation mode."   
     ::= { f3PtpL3PTPPortEntry 36 }

f3PtpL3PTPPortAutoAsymmetryCompStatus OBJECT-TYPE
    SYNTAX     CompensationStatus  
    MAX-ACCESS read-only
    STATUS     current
    DESCRIPTION
        "This object provides the automatic delay asymmetry 
        compensation status." 
     ::= { f3PtpL3PTPPortEntry 37 }

f3PtpL3PTPPortDelayAsymmetry OBJECT-TYPE
    SYNTAX     Integer32 (-10000000..10000000)
    MAX-ACCESS read-write
    STATUS     current
    DESCRIPTION
        "This object is used for manual configuration of delay asymmetry
        in ns if delay asymmetry compensation is Manual.
        Or for indication of the measured delay asymmetry if
        delay asymmetry compensation is automatic."
     ::= { f3PtpL3PTPPortEntry 38 }

f3PtpL3PTPPortStorageType OBJECT-TYPE
    SYNTAX     StorageType
    MAX-ACCESS read-create
    STATUS     current
    DESCRIPTION
            "The type of storage configured for this entry."
    ::= { f3PtpL3PTPPortEntry 39 }

f3PtpL3PTPPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpPTPPortRowStatus supported are
            createAndGo(4) and destroy(6).  All mandatory attributes
            must be specified in a single SNMP SET request with
            f3PtpPTPPortRowStatus value as createAndGo(4).
            Upon successful row creation, this object has a
            value of active(1).

            The f3PtpPTPPortRowStatus object may be modified if
            the associated instance of this object is equal to active(1)."
    ::= { f3PtpL3PTPPortEntry 40 }

f3PtpL3PTPPortDelayReqDestIpAddrType OBJECT-TYPE
    SYNTAX     PTPTransportMode
    MAX-ACCESS read-create
    STATUS     current
    DESCRIPTION
        "The type of transport mode address
        acceptable valuea are either unicast or multicast."   
     ::= { f3PtpL3PTPPortEntry 41 }

f3PtpL3PTPPortScaledLogVariance OBJECT-TYPE
    SYNTAX     Integer32 
    MAX-ACCESS read-only
    STATUS     current
    DESCRIPTION
            "This object indicates the Offset Scaled Log Variance of the clock that contains the port"
        ::= { f3PtpL3PTPPortEntry 42 }

f3PtpL3PTPPortClockAccuracy OBJECT-TYPE
    SYNTAX     Integer32 
    MAX-ACCESS read-only
    STATUS     current
    DESCRIPTION
            "This object indicates the Clock Accuracy of the clock that contains the port"
        ::= { f3PtpL3PTPPortEntry 43 }

f3PtpL3PTPPortGMIdentity OBJECT-TYPE
    SYNTAX     DisplayString (SIZE(0..16))
    MAX-ACCESS read-only
    STATUS     current
    DESCRIPTION
            "This object indicates the Grandmaster Identity of the clock that contains the port"
        ::= { f3PtpL3PTPPortEntry 44 }

f3PtpL3PTPPortStepsRemoved OBJECT-TYPE
    SYNTAX     Integer32 
    MAX-ACCESS read-only
    STATUS     current
    DESCRIPTION
            "This object indicates the number of Steps Removed for the port"
        ::= { f3PtpL3PTPPortEntry 45 }

f3PtpL3PTPPortVirtualPortCtrl OBJECT-TYPE                    
    SYNTAX      ToggleValue
    MAX-ACCESS  read-create
    STATUS      current
    DESCRIPTION
            "This object indicates if L3 PTP Port is virtual."
        ::= { f3PtpL3PTPPortEntry 46 }
        
f3PtpL3PTPPortLastRcvdAnnounceMsg OBJECT-TYPE
    SYNTAX     F3DisplayString 
    MAX-ACCESS read-only
    STATUS     current
    DESCRIPTION
        "This object specifies the last recieved announce message." 
    ::= { f3PtpL3PTPPortEntry 47 }
    
f3PtpL3PTPPortLastRcvdSyncMsg OBJECT-TYPE
    SYNTAX     F3DisplayString 
    MAX-ACCESS read-only
    STATUS     current
    DESCRIPTION
        "This object specifies the last recieved sync message." 
    ::= { f3PtpL3PTPPortEntry 48 }
    
f3PtpL3PTPPortLastRcvdDelayReqMsg OBJECT-TYPE
    SYNTAX     F3DisplayString 
    MAX-ACCESS read-only
    STATUS     current
    DESCRIPTION
        "This object specifies the last recieved delay request message." 
    ::= { f3PtpL3PTPPortEntry 49 }
    
f3PtpL3PTPPortLastRcvdDelayRspMsg OBJECT-TYPE
    SYNTAX     F3DisplayString 
    MAX-ACCESS read-only
    STATUS     current
    DESCRIPTION
        "This object specifies the last recieved response message." 
    ::= { f3PtpL3PTPPortEntry 50 } 
          
f3PtpL3PTPPortMaxLeaseDuration OBJECT-TYPE
    SYNTAX      Integer32 
    MAX-ACCESS  read-create
    STATUS      current
    DESCRIPTION
        "This object specifies the max lease duration."
    ::= { f3PtpL3PTPPortEntry 51 }

f3PtpL3PTPPortMaxSlavesSupported OBJECT-TYPE
    SYNTAX      Integer32 
    MAX-ACCESS  read-create
    STATUS      current
    DESCRIPTION
        "This object specifies the max slaves supported."
    ::= { f3PtpL3PTPPortEntry 52 }

f3PtpL3PTPPortMaxAnnounceMessageRate OBJECT-TYPE
    SYNTAX      AnnounceMsgRate 
    MAX-ACCESS  read-create
    STATUS      current
    DESCRIPTION
        "This object specifies the max announce message rate."
    ::= { f3PtpL3PTPPortEntry 53 }

f3PtpL3PTPPortMaxSyncMessageRate OBJECT-TYPE
    SYNTAX      SyncMsgRate 
    MAX-ACCESS  read-create
    STATUS      current
    DESCRIPTION
        "This object specifies the max sync message rate."
    ::= { f3PtpL3PTPPortEntry 54 }

f3PtpL3PTPPortMaxDelayRespMessageRate OBJECT-TYPE
    SYNTAX      DelayRespMsgRate 
    MAX-ACCESS  read-create
    STATUS      current
    DESCRIPTION
        "."
    ::= { f3PtpL3PTPPortEntry 55 }

f3PtpL3PTPPortMasterOnly OBJECT-TYPE
    SYNTAX      TruthValue 
    MAX-ACCESS  read-create
    STATUS      current
    DESCRIPTION
        "Whether this L3 PTPPort is MasterOnly or Dynamic."
    ::= { f3PtpL3PTPPortEntry 56 }

--
-- PERFORMANCE 
--
--
-- Access Port PTP Flow Point Current Statistics Table
--
f3PtpAccPortFlowPointStatsTable OBJECT-TYPE
    SYNTAX      SEQUENCE OF F3PtpAccPortFlowPointStatsEntry
    MAX-ACCESS  not-accessible
    STATUS      current
    DESCRIPTION
            "A collection of Access Port PTP Flow Point statistics.  
             These reflect the current data."
    ::= { f3PtpPerformanceObjects 1 }

f3PtpAccPortFlowPointStatsEntry OBJECT-TYPE
    SYNTAX      F3PtpAccPortFlowPointStatsEntry 
    MAX-ACCESS  not-accessible
    STATUS      current
    DESCRIPTION
            "A conceptual row in the f3PtpAccPortFlowPointStatsTable.
             Entries exist in this table for each Access Port Flow Point."
    INDEX { neIndex, shelfIndex, slotIndex, cmEthernetAccPortIndex, 
            f3PtpAccPortFlowPointIndex, f3PtpAccPortFlowPointStatsIndex }
    ::= { f3PtpAccPortFlowPointStatsTable 1 }

F3PtpAccPortFlowPointStatsEntry ::= SEQUENCE {
    f3PtpAccPortFlowPointStatsIndex                  Integer32,
    f3PtpAccPortFlowPointStatsIntervalType           CmPmIntervalType,
    f3PtpAccPortFlowPointStatsValid                  TruthValue,
    f3PtpAccPortFlowPointStatsAction                 CmPmBinAction,
    f3PtpAccPortFlowPointStatsAnnouncesRx            PerfCounter64,
    f3PtpAccPortFlowPointStatsAnnouncesTx            PerfCounter64,
    f3PtpAccPortFlowPointStatsSyncsRx                PerfCounter64,
    f3PtpAccPortFlowPointStatsSyncsTx                PerfCounter64,
    f3PtpAccPortFlowPointStatsFollowupsRx            PerfCounter64,
    f3PtpAccPortFlowPointStatsFollowupsTx            PerfCounter64,
    f3PtpAccPortFlowPointStatsDelayReqsRx            PerfCounter64,
    f3PtpAccPortFlowPointStatsDelayReqsTx            PerfCounter64,
    f3PtpAccPortFlowPointStatsDelayRspsRx            PerfCounter64,
    f3PtpAccPortFlowPointStatsDelayRspsTx            PerfCounter64,
    f3PtpAccPortFlowPointStatsPDelayReqsRx           PerfCounter64,
    f3PtpAccPortFlowPointStatsPDelayReqsTx           PerfCounter64,
    f3PtpAccPortFlowPointStatsPDelayRspsRx           PerfCounter64,
    f3PtpAccPortFlowPointStatsPDelayRspsTx           PerfCounter64,
    f3PtpAccPortFlowPointStatsPDelayRspFollowupsRx   PerfCounter64,
    f3PtpAccPortFlowPointStatsPDelayRspFollowupsTx   PerfCounter64,
    f3PtpAccPortFlowPointStatsSignalingRx            PerfCounter64,
    f3PtpAccPortFlowPointStatsSignalingTx            PerfCounter64,
    f3PtpAccPortFlowPointStatsMgmtFramesRx           PerfCounter64,
    f3PtpAccPortFlowPointStatsMgmtFramesTx           PerfCounter64,
    f3PtpAccPortFlowPointStatsPtpUnknownsRx          PerfCounter64,
    f3PtpAccPortFlowPointStatsPtpUnknownsTx          PerfCounter64,
    f3PtpAccPortFlowPointStatsMinSyncResTime         Unsigned32,
    f3PtpAccPortFlowPointStatsMaxSyncResTime         Unsigned32,
    f3PtpAccPortFlowPointStatsAvgSyncResTime         Unsigned32,
    f3PtpAccPortFlowPointStatsMinDelayReqResTime     Unsigned32,
    f3PtpAccPortFlowPointStatsMaxDelayReqResTime     Unsigned32,
    f3PtpAccPortFlowPointStatsAvgDelayReqResTime     Unsigned32,
    f3PtpAccPortFlowPointStatsMinPDelayReqResTime    Unsigned32,
    f3PtpAccPortFlowPointStatsMaxPDelayReqResTime    Unsigned32,
    f3PtpAccPortFlowPointStatsAvgPDelayReqResTime    Unsigned32,
    f3PtpAccPortFlowPointStatsMinPDelayRspResTime    Unsigned32,
    f3PtpAccPortFlowPointStatsMaxPDelayRspResTime    Unsigned32,
    f3PtpAccPortFlowPointStatsAvgPDelayRspResTime    Unsigned32,
    f3PtpAccPortFlowPointStatsDestMciNoMatchDiscards PerfCounter64,
    f3PtpAccPortFlowPointStatsTagNoMatchDiscards     PerfCounter64
}

f3PtpAccPortFlowPointStatsIndex OBJECT-TYPE
    SYNTAX      Integer32 (1..4)
    MAX-ACCESS  not-accessible 
    STATUS      current
    DESCRIPTION
            "An arbitrary integer index value used to uniquely identify
            this Access Port PTP Flow Point statistics entry. 
            1 - 15min
            2 - 1day
            3 - rollover
            4 - 5min"
    ::= { f3PtpAccPortFlowPointStatsEntry 1 }

f3PtpAccPortFlowPointStatsIntervalType OBJECT-TYPE
    SYNTAX      CmPmIntervalType
    MAX-ACCESS  read-only
    STATUS      current
    DESCRIPTION
            "Indicates the type of collection, i.e. whether it is
             15 Min, 1 Day or rollover."
    ::= { f3PtpAccPortFlowPointStatsEntry 2 }

f3PtpAccPortFlowPointStatsValid OBJECT-TYPE
    SYNTAX      TruthValue
    MAX-ACCESS  read-only
    STATUS      current
    DESCRIPTION
            "Indicates the validity of the bin."
    ::= { f3PtpAccPortFlowPointStatsEntry 3 }

f3PtpAccPortFlowPointStatsAction OBJECT-TYPE
    SYNTAX      CmPmBinAction
    MAX-ACCESS  read-write
    STATUS      current
    DESCRIPTION
            "Allows the Manager to clear the bin."
    ::= { f3PtpAccPortFlowPointStatsEntry 4 }

f3PtpAccPortFlowPointStatsAnnouncesRx OBJECT-TYPE
     SYNTAX     PerfCounter64
     MAX-ACCESS read-only
     STATUS     current
     DESCRIPTION
         "Number of PTP Announce messages received on the PTP Flow Point."
     ::= { f3PtpAccPortFlowPointStatsEntry 5 }

f3PtpAccPortFlowPointStatsAnnouncesTx OBJECT-TYPE
     SYNTAX     PerfCounter64
     MAX-ACCESS read-only
     STATUS     current
     DESCRIPTION
         "Number of Announce Messages transmitted on the PTP Flow Point.
          This object is applicable for transparent clocks."
     ::= { f3PtpAccPortFlowPointStatsEntry 6 }

f3PtpAccPortFlowPointStatsSyncsRx OBJECT-TYPE
     SYNTAX     PerfCounter64
     MAX-ACCESS read-only
     STATUS     current
     DESCRIPTION
         "Number of Sync Messages received on the PTP Flow Point."
     ::= { f3PtpAccPortFlowPointStatsEntry 7 }

f3PtpAccPortFlowPointStatsSyncsTx OBJECT-TYPE
     SYNTAX     PerfCounter64
     MAX-ACCESS read-only
     STATUS     current
     DESCRIPTION
         "Number of Sync Messages transmitted on the PTP Flow Point.
          This object is applicable for transparent clocks."
     ::= { f3PtpAccPortFlowPointStatsEntry 8 }

f3PtpAccPortFlowPointStatsFollowupsRx OBJECT-TYPE
     SYNTAX     PerfCounter64
     MAX-ACCESS read-only
     STATUS     current
     DESCRIPTION
         "Number of Follow up Messages received on the PTP Flow Point."
     ::= { f3PtpAccPortFlowPointStatsEntry 9 }

f3PtpAccPortFlowPointStatsFollowupsTx OBJECT-TYPE
     SYNTAX     PerfCounter64
     MAX-ACCESS read-only
     STATUS     current
     DESCRIPTION
         "Number of Follow up Messages transmitted on the PTP Flow Point."
     ::= { f3PtpAccPortFlowPointStatsEntry 10 }

f3PtpAccPortFlowPointStatsDelayReqsRx OBJECT-TYPE
     SYNTAX     PerfCounter64
     MAX-ACCESS read-only
     STATUS     current
     DESCRIPTION
         "Number of Delay Request Messages received on the PTP Flow Point."
     ::= { f3PtpAccPortFlowPointStatsEntry 11 }

f3PtpAccPortFlowPointStatsDelayReqsTx OBJECT-TYPE
     SYNTAX     PerfCounter64
     MAX-ACCESS read-only
     STATUS     current
     DESCRIPTION
         "Number of Delay Request Messages transmitted on the PTP Flow Point."
     ::= { f3PtpAccPortFlowPointStatsEntry 12 }

f3PtpAccPortFlowPointStatsDelayRspsRx OBJECT-TYPE
     SYNTAX     PerfCounter64
     MAX-ACCESS read-only
     STATUS     current
     DESCRIPTION
         "Number of Delay Response Messages received on the PTP Flow Point."
     ::= { f3PtpAccPortFlowPointStatsEntry 13 }

f3PtpAccPortFlowPointStatsDelayRspsTx OBJECT-TYPE
     SYNTAX     PerfCounter64
     MAX-ACCESS read-only
     STATUS     current
     DESCRIPTION
         "Number of Delay Response Messages transmitted on the PTP Flow Point."
     ::= { f3PtpAccPortFlowPointStatsEntry 14 }

f3PtpAccPortFlowPointStatsPDelayReqsRx OBJECT-TYPE
     SYNTAX     PerfCounter64
     MAX-ACCESS read-only
     STATUS     current
     DESCRIPTION
         "Number of Peer Delay Request Messages received on the PTP Flow Point."
     ::= { f3PtpAccPortFlowPointStatsEntry 15 }

f3PtpAccPortFlowPointStatsPDelayReqsTx OBJECT-TYPE
     SYNTAX     PerfCounter64
     MAX-ACCESS read-only
     STATUS     current
     DESCRIPTION
         "Number of Peer Delay Request Messages transmitted on the PTP Flow Point."
     ::= { f3PtpAccPortFlowPointStatsEntry 16 }

f3PtpAccPortFlowPointStatsPDelayRspsRx OBJECT-TYPE
     SYNTAX     PerfCounter64
     MAX-ACCESS read-only
     STATUS     current
     DESCRIPTION
         "Number of Peer Delay Response Messages received on the PTP Flow Point."
     ::= { f3PtpAccPortFlowPointStatsEntry 17 }

f3PtpAccPortFlowPointStatsPDelayRspsTx OBJECT-TYPE
     SYNTAX     PerfCounter64
     MAX-ACCESS read-only
     STATUS     current
     DESCRIPTION
         "Number of Peer Delay Response Messages transmitted on the PTP Flow Point."
     ::= { f3PtpAccPortFlowPointStatsEntry 18 }

f3PtpAccPortFlowPointStatsPDelayRspFollowupsRx OBJECT-TYPE
     SYNTAX     PerfCounter64
     MAX-ACCESS read-only
     STATUS     current
     DESCRIPTION
         "Number of Peer Delay Response Followup Messages received on the PTP Flow Point."
     ::= { f3PtpAccPortFlowPointStatsEntry 19 }

f3PtpAccPortFlowPointStatsPDelayRspFollowupsTx OBJECT-TYPE
     SYNTAX     PerfCounter64
     MAX-ACCESS read-only
     STATUS     current
     DESCRIPTION
         "Number of Peer Delay Response Followup Messages transmitted on the PTP Flow Point."
     ::= { f3PtpAccPortFlowPointStatsEntry 20 }

f3PtpAccPortFlowPointStatsSignalingRx OBJECT-TYPE
     SYNTAX     PerfCounter64
     MAX-ACCESS read-only
     STATUS     current
     DESCRIPTION
         "Number of PTP Signaling Messages received on the PTP Flow Point."
     ::= { f3PtpAccPortFlowPointStatsEntry 21 }

f3PtpAccPortFlowPointStatsSignalingTx OBJECT-TYPE
     SYNTAX     PerfCounter64
     MAX-ACCESS read-only
     STATUS     current
     DESCRIPTION
         "Number of PTP Signaling Messages Messages transmitted on the PTP Flow Point."
     ::= { f3PtpAccPortFlowPointStatsEntry 22 }

f3PtpAccPortFlowPointStatsMgmtFramesRx OBJECT-TYPE
     SYNTAX     PerfCounter64
     MAX-ACCESS read-only
     STATUS     current
     DESCRIPTION
         "Number of PTP Management Frames received on the PTP Flow Point."
     ::= { f3PtpAccPortFlowPointStatsEntry 23 }

f3PtpAccPortFlowPointStatsMgmtFramesTx OBJECT-TYPE
     SYNTAX     PerfCounter64
     MAX-ACCESS read-only
     STATUS     current
     DESCRIPTION
         "Number of PTP Management Frames Messages transmitted on the PTP Flow Point."
     ::= { f3PtpAccPortFlowPointStatsEntry 24 }

f3PtpAccPortFlowPointStatsPtpUnknownsRx OBJECT-TYPE
     SYNTAX     PerfCounter64
     MAX-ACCESS read-only
     STATUS     current
     DESCRIPTION
         "Number of Unknown PTP Messages received on the PTP Flow Point."
     ::= { f3PtpAccPortFlowPointStatsEntry 25 }

f3PtpAccPortFlowPointStatsPtpUnknownsTx OBJECT-TYPE
     SYNTAX     PerfCounter64
     MAX-ACCESS read-only
     STATUS     current
     DESCRIPTION
         "Number of Unknown PTP Messages transmitted on the PTP Flow Point."
     ::= { f3PtpAccPortFlowPointStatsEntry 26 }

f3PtpAccPortFlowPointStatsMinSyncResTime OBJECT-TYPE
     SYNTAX     Unsigned32
     MAX-ACCESS read-only
     STATUS     deprecated
     DESCRIPTION
         "The minimum residence time for PTP Sync messages."
     ::= { f3PtpAccPortFlowPointStatsEntry 27 }

f3PtpAccPortFlowPointStatsMaxSyncResTime OBJECT-TYPE
     SYNTAX     Unsigned32
     MAX-ACCESS read-only
     STATUS     deprecated
     DESCRIPTION
         "The maximum residence time for PTP Sync messages."
     ::= { f3PtpAccPortFlowPointStatsEntry 28 }

f3PtpAccPortFlowPointStatsAvgSyncResTime OBJECT-TYPE
     SYNTAX     Unsigned32
     MAX-ACCESS read-only
     STATUS     deprecated
     DESCRIPTION
         "The average residence time for PTP Sync messages."
     ::= { f3PtpAccPortFlowPointStatsEntry 29 }

f3PtpAccPortFlowPointStatsMinDelayReqResTime OBJECT-TYPE
     SYNTAX     Unsigned32
     MAX-ACCESS read-only
     STATUS     deprecated
     DESCRIPTION
         "The minimum residence time for PTP Delay Request messages."
     ::= { f3PtpAccPortFlowPointStatsEntry 30 }

f3PtpAccPortFlowPointStatsMaxDelayReqResTime OBJECT-TYPE
     SYNTAX     Unsigned32
     MAX-ACCESS read-only
     STATUS     deprecated
     DESCRIPTION
         "The maximum residence time for PTP Delay Request messages."
     ::= { f3PtpAccPortFlowPointStatsEntry 31 }

f3PtpAccPortFlowPointStatsAvgDelayReqResTime OBJECT-TYPE
     SYNTAX     Unsigned32
     MAX-ACCESS read-only
     STATUS     deprecated
     DESCRIPTION
         "The average residence time for PTP Delay Request messages."
     ::= { f3PtpAccPortFlowPointStatsEntry 32 }

f3PtpAccPortFlowPointStatsMinPDelayReqResTime OBJECT-TYPE
     SYNTAX     Unsigned32
     MAX-ACCESS read-only
     STATUS     deprecated
     DESCRIPTION
         "The minimum residence time for PTP Peer Delay Request messages."
     ::= { f3PtpAccPortFlowPointStatsEntry 33 }

f3PtpAccPortFlowPointStatsMaxPDelayReqResTime OBJECT-TYPE
     SYNTAX     Unsigned32
     MAX-ACCESS read-only
     STATUS     deprecated
     DESCRIPTION
         "The maximum residence time for PTP Peer Delay Request messages."
     ::= { f3PtpAccPortFlowPointStatsEntry 34 }

f3PtpAccPortFlowPointStatsAvgPDelayReqResTime OBJECT-TYPE
     SYNTAX     Unsigned32
     MAX-ACCESS read-only
     STATUS     deprecated
     DESCRIPTION
         "The average residence time for PTP Peer Delay Request messages."
     ::= { f3PtpAccPortFlowPointStatsEntry 35 }

f3PtpAccPortFlowPointStatsMinPDelayRspResTime OBJECT-TYPE
     SYNTAX     Unsigned32
     MAX-ACCESS read-only
     STATUS     deprecated
     DESCRIPTION
         "The minimum residence time for PTP Peer Delay Response messages."
     ::= { f3PtpAccPortFlowPointStatsEntry 36 }

f3PtpAccPortFlowPointStatsMaxPDelayRspResTime OBJECT-TYPE
     SYNTAX     Unsigned32
     MAX-ACCESS read-only
     STATUS     deprecated
     DESCRIPTION
         "The maximum residence time for PTP Peer Delay Response messages."
     ::= { f3PtpAccPortFlowPointStatsEntry 37 }

f3PtpAccPortFlowPointStatsAvgPDelayRspResTime OBJECT-TYPE
     SYNTAX     Unsigned32
     MAX-ACCESS read-only
     STATUS     deprecated
     DESCRIPTION
         "The average residence time for PTP Peer Delay Response messages."
     ::= { f3PtpAccPortFlowPointStatsEntry 38 }

f3PtpAccPortFlowPointStatsDestMciNoMatchDiscards OBJECT-TYPE
     SYNTAX     PerfCounter64
     MAX-ACCESS read-write
     STATUS     current
     DESCRIPTION
         "The dest MCI no match discards messages."
     ::= { f3PtpAccPortFlowPointStatsEntry 39 }

f3PtpAccPortFlowPointStatsTagNoMatchDiscards OBJECT-TYPE
     SYNTAX     PerfCounter64
     MAX-ACCESS read-write
     STATUS     current
     DESCRIPTION
         "The tag no match discards messages."
     ::= { f3PtpAccPortFlowPointStatsEntry 40 }

--
-- Access Port PTP Flow Point History Table
--
f3PtpAccPortFlowPointHistoryTable OBJECT-TYPE
    SYNTAX      SEQUENCE OF F3PtpAccPortFlowPointHistoryEntry
    MAX-ACCESS  not-accessible
    STATUS      current
    DESCRIPTION
            "A collection of Access Port PTP Flow Point history statistics.  
             These reflect the history data."
    ::= { f3PtpPerformanceObjects 2 }

f3PtpAccPortFlowPointHistoryEntry OBJECT-TYPE
    SYNTAX      F3PtpAccPortFlowPointHistoryEntry 
    MAX-ACCESS  not-accessible
    STATUS      current
    DESCRIPTION
            "A conceptual row in the f3PtpAccPortFlowPointHistoryTable.
             Entries exist in this table for each Access Port Flow Point."
    INDEX { neIndex, shelfIndex, slotIndex, cmEthernetAccPortIndex, 
            f3PtpAccPortFlowPointIndex, f3PtpAccPortFlowPointStatsIndex, 
            f3PtpAccPortFlowPointHistoryIndex }
    ::= { f3PtpAccPortFlowPointHistoryTable 1 }

F3PtpAccPortFlowPointHistoryEntry ::= SEQUENCE {
    f3PtpAccPortFlowPointHistoryIndex                  Integer32,
    f3PtpAccPortFlowPointHistoryTime                   DateAndTime,
    f3PtpAccPortFlowPointHistoryValid                  TruthValue,
    f3PtpAccPortFlowPointHistoryAction                 CmPmBinAction,
    f3PtpAccPortFlowPointHistoryAnnouncesRx            PerfCounter64,
    f3PtpAccPortFlowPointHistoryAnnouncesTx            PerfCounter64,
    f3PtpAccPortFlowPointHistorySyncsRx                PerfCounter64,
    f3PtpAccPortFlowPointHistorySyncsTx                PerfCounter64,
    f3PtpAccPortFlowPointHistoryFollowupsRx            PerfCounter64,
    f3PtpAccPortFlowPointHistoryFollowupsTx            PerfCounter64,
    f3PtpAccPortFlowPointHistoryDelayReqsRx            PerfCounter64,
    f3PtpAccPortFlowPointHistoryDelayReqsTx            PerfCounter64,
    f3PtpAccPortFlowPointHistoryDelayRspsRx            PerfCounter64,
    f3PtpAccPortFlowPointHistoryDelayRspsTx            PerfCounter64,
    f3PtpAccPortFlowPointHistoryPDelayReqsRx           PerfCounter64,
    f3PtpAccPortFlowPointHistoryPDelayReqsTx           PerfCounter64,
    f3PtpAccPortFlowPointHistoryPDelayRspsRx           PerfCounter64,
    f3PtpAccPortFlowPointHistoryPDelayRspsTx           PerfCounter64,
    f3PtpAccPortFlowPointHistoryPDelayRspFollowupsRx   PerfCounter64,
    f3PtpAccPortFlowPointHistoryPDelayRspFollowupsTx   PerfCounter64,
    f3PtpAccPortFlowPointHistorySignalingRx            PerfCounter64,
    f3PtpAccPortFlowPointHistorySignalingTx            PerfCounter64,
    f3PtpAccPortFlowPointHistoryMgmtFramesRx           PerfCounter64,
    f3PtpAccPortFlowPointHistoryMgmtFramesTx           PerfCounter64,
    f3PtpAccPortFlowPointHistoryPtpUnknownsRx          PerfCounter64,
    f3PtpAccPortFlowPointHistoryPtpUnknownsTx          PerfCounter64,
    f3PtpAccPortFlowPointHistoryMinSyncResTime         Unsigned32,
    f3PtpAccPortFlowPointHistoryMaxSyncResTime         Unsigned32,
    f3PtpAccPortFlowPointHistoryAvgSyncResTime         Unsigned32,
    f3PtpAccPortFlowPointHistoryMinDelayReqResTime     Unsigned32,
    f3PtpAccPortFlowPointHistoryMaxDelayReqResTime     Unsigned32,
    f3PtpAccPortFlowPointHistoryAvgDelayReqResTime     Unsigned32,
    f3PtpAccPortFlowPointHistoryMinPDelayReqResTime    Unsigned32,
    f3PtpAccPortFlowPointHistoryMaxPDelayReqResTime    Unsigned32,
    f3PtpAccPortFlowPointHistoryAvgPDelayReqResTime    Unsigned32,
    f3PtpAccPortFlowPointHistoryMinPDelayRspResTime    Unsigned32,
    f3PtpAccPortFlowPointHistoryMaxPDelayRspResTime    Unsigned32,
    f3PtpAccPortFlowPointHistoryAvgPDelayRspResTime    Unsigned32,
    f3PtpAccPortFlowPointHistoryDestMciNoMatchDiscards PerfCounter64,
    f3PtpAccPortFlowPointHistoryTagNoMatchDiscards     PerfCounter64
}

f3PtpAccPortFlowPointHistoryIndex OBJECT-TYPE
    SYNTAX      Integer32 (1..32)
    MAX-ACCESS  not-accessible 
    STATUS      current
    DESCRIPTION
            "An arbitrary integer index value used to uniquely identify
            this Ethernet Access Port PTP Flow point PM history entry."
    ::= { f3PtpAccPortFlowPointHistoryEntry 1 }

f3PtpAccPortFlowPointHistoryTime OBJECT-TYPE
    SYNTAX      DateAndTime
    MAX-ACCESS  read-only
    STATUS      current
    DESCRIPTION
            "Indicates the time of history bin creation." 
    ::= { f3PtpAccPortFlowPointHistoryEntry 2 }

f3PtpAccPortFlowPointHistoryValid OBJECT-TYPE
    SYNTAX      TruthValue
    MAX-ACCESS  read-only
    STATUS      current
    DESCRIPTION
            "Indicates the validity of the bin."
    ::= { f3PtpAccPortFlowPointHistoryEntry 3 }

f3PtpAccPortFlowPointHistoryAction OBJECT-TYPE
    SYNTAX      CmPmBinAction
    MAX-ACCESS  read-write
    STATUS      current
    DESCRIPTION
            "Allows the Manager to clear the bin."
    ::= { f3PtpAccPortFlowPointHistoryEntry 4 }

f3PtpAccPortFlowPointHistoryAnnouncesRx OBJECT-TYPE
     SYNTAX     PerfCounter64
     MAX-ACCESS read-only
     STATUS     current
     DESCRIPTION
         "Number of PTP Announce messages received on the PTP Flow Point."
     ::= { f3PtpAccPortFlowPointHistoryEntry 5 }

f3PtpAccPortFlowPointHistoryAnnouncesTx OBJECT-TYPE
     SYNTAX     PerfCounter64
     MAX-ACCESS read-only
     STATUS     current
     DESCRIPTION
         "Number of Announce Messages transmitted on the PTP Flow Point.
          This object is applicable for transparent clocks."
     ::= { f3PtpAccPortFlowPointHistoryEntry 6 }

f3PtpAccPortFlowPointHistorySyncsRx OBJECT-TYPE
     SYNTAX     PerfCounter64
     MAX-ACCESS read-only
     STATUS     current
     DESCRIPTION
         "Number of Sync Messages received on the PTP Flow Point."
     ::= { f3PtpAccPortFlowPointHistoryEntry 7 }

f3PtpAccPortFlowPointHistorySyncsTx OBJECT-TYPE
     SYNTAX     PerfCounter64
     MAX-ACCESS read-only
     STATUS     current
     DESCRIPTION
         "Number of Sync Messages transmitted on the PTP Flow Point.
          This object is applicable for transparent clocks."
     ::= { f3PtpAccPortFlowPointHistoryEntry 8 }

f3PtpAccPortFlowPointHistoryFollowupsRx OBJECT-TYPE
     SYNTAX     PerfCounter64
     MAX-ACCESS read-only
     STATUS     current
     DESCRIPTION
         "Number of Follow up Messages received on the PTP Flow Point."
     ::= { f3PtpAccPortFlowPointHistoryEntry 9 }

f3PtpAccPortFlowPointHistoryFollowupsTx OBJECT-TYPE
     SYNTAX     PerfCounter64
     MAX-ACCESS read-only
     STATUS     current
     DESCRIPTION
         "Number of Follow up Messages transmitted on the PTP Flow Point."
     ::= { f3PtpAccPortFlowPointHistoryEntry 10 }

f3PtpAccPortFlowPointHistoryDelayReqsRx OBJECT-TYPE
     SYNTAX     PerfCounter64
     MAX-ACCESS read-only
     STATUS     current
     DESCRIPTION
         "Number of Delay Request Messages received on the PTP Flow Point."
     ::= { f3PtpAccPortFlowPointHistoryEntry 11 }

f3PtpAccPortFlowPointHistoryDelayReqsTx OBJECT-TYPE
     SYNTAX     PerfCounter64
     MAX-ACCESS read-only
     STATUS     current
     DESCRIPTION
         "Number of Delay Request Messages transmitted on the PTP Flow Point."
     ::= { f3PtpAccPortFlowPointHistoryEntry 12 }

f3PtpAccPortFlowPointHistoryDelayRspsRx OBJECT-TYPE
     SYNTAX     PerfCounter64
     MAX-ACCESS read-only
     STATUS     current
     DESCRIPTION
         "Number of Delay Response Messages received on the PTP Flow Point."
     ::= { f3PtpAccPortFlowPointHistoryEntry 13 }

f3PtpAccPortFlowPointHistoryDelayRspsTx OBJECT-TYPE
     SYNTAX     PerfCounter64
     MAX-ACCESS read-only
     STATUS     current
     DESCRIPTION
         "Number of Delay Response Messages transmitted on the PTP Flow Point."
     ::= { f3PtpAccPortFlowPointHistoryEntry 14 }

f3PtpAccPortFlowPointHistoryPDelayReqsRx OBJECT-TYPE
     SYNTAX     PerfCounter64
     MAX-ACCESS read-only
     STATUS     current
     DESCRIPTION
         "Number of Peer Delay Request Messages received on the PTP Flow Point."
     ::= { f3PtpAccPortFlowPointHistoryEntry 15 }

f3PtpAccPortFlowPointHistoryPDelayReqsTx OBJECT-TYPE
     SYNTAX     PerfCounter64
     MAX-ACCESS read-only
     STATUS     current
     DESCRIPTION
         "Number of Peer Delay Request Messages transmitted on the PTP Flow Point."
     ::= { f3PtpAccPortFlowPointHistoryEntry 16 }

f3PtpAccPortFlowPointHistoryPDelayRspsRx OBJECT-TYPE
     SYNTAX     PerfCounter64
     MAX-ACCESS read-only
     STATUS     current
     DESCRIPTION
         "Number of Peer Delay Response Messages received on the PTP Flow Point."
     ::= { f3PtpAccPortFlowPointHistoryEntry 17 }

f3PtpAccPortFlowPointHistoryPDelayRspsTx OBJECT-TYPE
     SYNTAX     PerfCounter64
     MAX-ACCESS read-only
     STATUS     current
     DESCRIPTION
         "Number of Peer Delay Response Messages transmitted on the PTP Flow Point."
     ::= { f3PtpAccPortFlowPointHistoryEntry 18 }

f3PtpAccPortFlowPointHistoryPDelayRspFollowupsRx OBJECT-TYPE
     SYNTAX     PerfCounter64
     MAX-ACCESS read-only
     STATUS     current
     DESCRIPTION
         "Number of Peer Delay Response Followup Messages received on the PTP Flow Point."
     ::= { f3PtpAccPortFlowPointHistoryEntry 19 }

f3PtpAccPortFlowPointHistoryPDelayRspFollowupsTx OBJECT-TYPE
     SYNTAX     PerfCounter64
     MAX-ACCESS read-only
     STATUS     current
     DESCRIPTION
         "Number of Peer Delay Response Followup Messages transmitted on the PTP Flow Point."
     ::= { f3PtpAccPortFlowPointHistoryEntry 20 }

f3PtpAccPortFlowPointHistorySignalingRx OBJECT-TYPE
     SYNTAX     PerfCounter64
     MAX-ACCESS read-only
     STATUS     current
     DESCRIPTION
         "Number of PTP Signaling Messages received on the PTP Flow Point."
     ::= { f3PtpAccPortFlowPointHistoryEntry 21 }

f3PtpAccPortFlowPointHistorySignalingTx OBJECT-TYPE
     SYNTAX     PerfCounter64
     MAX-ACCESS read-only
     STATUS     current
     DESCRIPTION
         "Number of PTP Signaling Messages Messages transmitted on the PTP Flow Point."
     ::= { f3PtpAccPortFlowPointHistoryEntry 22 }

f3PtpAccPortFlowPointHistoryMgmtFramesRx OBJECT-TYPE
     SYNTAX     PerfCounter64
     MAX-ACCESS read-only
     STATUS     current
     DESCRIPTION
         "Number of PTP Management Frames received on the PTP Flow Point."
     ::= { f3PtpAccPortFlowPointHistoryEntry 23 }

f3PtpAccPortFlowPointHistoryMgmtFramesTx OBJECT-TYPE
     SYNTAX     PerfCounter64
     MAX-ACCESS read-only
     STATUS     current
     DESCRIPTION
         "Number of PTP Management Frames Messages transmitted on the PTP Flow Point."
     ::= { f3PtpAccPortFlowPointHistoryEntry 24 }

f3PtpAccPortFlowPointHistoryPtpUnknownsRx OBJECT-TYPE
     SYNTAX     PerfCounter64
     MAX-ACCESS read-only
     STATUS     current
     DESCRIPTION
         "Number of Unknown PTP Messages received on the PTP Flow Point."
     ::= { f3PtpAccPortFlowPointHistoryEntry 25 }

f3PtpAccPortFlowPointHistoryPtpUnknownsTx OBJECT-TYPE
     SYNTAX     PerfCounter64
     MAX-ACCESS read-only
     STATUS     current
     DESCRIPTION
         "Number of Unknown PTP Messages transmitted on the PTP Flow Point."
     ::= { f3PtpAccPortFlowPointHistoryEntry 26 }

f3PtpAccPortFlowPointHistoryMinSyncResTime OBJECT-TYPE
     SYNTAX     Unsigned32
     MAX-ACCESS read-only
     STATUS     deprecated
     DESCRIPTION
         "The minimum residence time for PTP Sync messages."
     ::= { f3PtpAccPortFlowPointHistoryEntry 27 }

f3PtpAccPortFlowPointHistoryMaxSyncResTime OBJECT-TYPE
     SYNTAX     Unsigned32
     MAX-ACCESS read-only
     STATUS     deprecated
     DESCRIPTION
         "The maximum residence time for PTP Sync messages."
     ::= { f3PtpAccPortFlowPointHistoryEntry 28 }

f3PtpAccPortFlowPointHistoryAvgSyncResTime OBJECT-TYPE
     SYNTAX     Unsigned32
     MAX-ACCESS read-only
     STATUS     deprecated
     DESCRIPTION
         "The average residence time for PTP Sync messages."
     ::= { f3PtpAccPortFlowPointHistoryEntry 29 }

f3PtpAccPortFlowPointHistoryMinDelayReqResTime OBJECT-TYPE
     SYNTAX     Unsigned32
     MAX-ACCESS read-only
     STATUS     deprecated
     DESCRIPTION
         "The minimum residence time for PTP Delay Request messages."
     ::= { f3PtpAccPortFlowPointHistoryEntry 30 }

f3PtpAccPortFlowPointHistoryMaxDelayReqResTime OBJECT-TYPE
     SYNTAX     Unsigned32
     MAX-ACCESS read-only
     STATUS     deprecated
     DESCRIPTION
         "The maximum residence time for PTP Delay Request messages."
     ::= { f3PtpAccPortFlowPointHistoryEntry 31 }

f3PtpAccPortFlowPointHistoryAvgDelayReqResTime OBJECT-TYPE
     SYNTAX     Unsigned32
     MAX-ACCESS read-only
     STATUS     deprecated
     DESCRIPTION
         "The average residence time for PTP Delay Request messages."
     ::= { f3PtpAccPortFlowPointHistoryEntry 32 }

f3PtpAccPortFlowPointHistoryMinPDelayReqResTime OBJECT-TYPE
     SYNTAX     Unsigned32
     MAX-ACCESS read-only
     STATUS     deprecated
     DESCRIPTION
         "The minimum residence time for PTP Peer Delay Request messages."
     ::= { f3PtpAccPortFlowPointHistoryEntry 33 }

f3PtpAccPortFlowPointHistoryMaxPDelayReqResTime OBJECT-TYPE
     SYNTAX     Unsigned32
     MAX-ACCESS read-only
     STATUS     deprecated
     DESCRIPTION
         "The maximum residence time for PTP Peer Delay Request messages."
     ::= { f3PtpAccPortFlowPointHistoryEntry 34 }

f3PtpAccPortFlowPointHistoryAvgPDelayReqResTime OBJECT-TYPE
     SYNTAX     Unsigned32
     MAX-ACCESS read-only
     STATUS     deprecated
     DESCRIPTION
         "The average residence time for PTP Peer Delay Request messages."
     ::= { f3PtpAccPortFlowPointHistoryEntry 35 }

f3PtpAccPortFlowPointHistoryMinPDelayRspResTime OBJECT-TYPE
     SYNTAX     Unsigned32
     MAX-ACCESS read-only
     STATUS     deprecated
     DESCRIPTION
         "The minimum residence time for PTP Peer Delay Response messages."
     ::= { f3PtpAccPortFlowPointHistoryEntry 36 }

f3PtpAccPortFlowPointHistoryMaxPDelayRspResTime OBJECT-TYPE
     SYNTAX     Unsigned32
     MAX-ACCESS read-only
     STATUS     deprecated
     DESCRIPTION
         "The maximum residence time for PTP Peer Delay Response messages."
     ::= { f3PtpAccPortFlowPointHistoryEntry 37 }

f3PtpAccPortFlowPointHistoryAvgPDelayRspResTime OBJECT-TYPE
     SYNTAX     Unsigned32
     MAX-ACCESS read-only
     STATUS     deprecated
     DESCRIPTION
         "The average residence time for PTP Peer Delay Response messages."
     ::= { f3PtpAccPortFlowPointHistoryEntry 38 }

f3PtpAccPortFlowPointHistoryDestMciNoMatchDiscards OBJECT-TYPE
     SYNTAX     PerfCounter64
     MAX-ACCESS read-write
     STATUS     current
     DESCRIPTION
         "The dest MCI no match discards messages."
     ::= { f3PtpAccPortFlowPointHistoryEntry 39 }

f3PtpAccPortFlowPointHistoryTagNoMatchDiscards OBJECT-TYPE
     SYNTAX     PerfCounter64
     MAX-ACCESS read-write
     STATUS     current
     DESCRIPTION
         "The tag no match discards messages."
     ::= { f3PtpAccPortFlowPointHistoryEntry 40 }

--
-- Access Port PTP Flow Point Threshold Table
--
f3PtpAccPortFlowPointThresholdTable OBJECT-TYPE
    SYNTAX      SEQUENCE OF F3PtpAccPortFlowPointThresholdEntry
    MAX-ACCESS  not-accessible
    STATUS      current
    DESCRIPTION
            "A table of entries that allow manageability of Access Port PTP Flow Point
             Thresholds."
    ::= { f3PtpPerformanceObjects 3 }

f3PtpAccPortFlowPointThresholdEntry OBJECT-TYPE
    SYNTAX      F3PtpAccPortFlowPointThresholdEntry
    MAX-ACCESS  not-accessible
    STATUS      current
    DESCRIPTION
            "A conceptual row in the f3PtpAccPortFlowPointThresholdTable."
    INDEX { neIndex, shelfIndex, slotIndex, cmEthernetAccPortIndex, 
            f3PtpAccPortFlowPointIndex, f3PtpAccPortFlowPointStatsIndex, 
            f3PtpAccPortFlowPointThresholdIndex }
    ::= { f3PtpAccPortFlowPointThresholdTable 1 }

F3PtpAccPortFlowPointThresholdEntry ::= SEQUENCE {
    f3PtpAccPortFlowPointThresholdIndex       Integer32,
    f3PtpAccPortFlowPointThresholdInterval    CmPmIntervalType,
    f3PtpAccPortFlowPointThresholdVariable    VariablePointer,
    f3PtpAccPortFlowPointThresholdValueLo     Unsigned32,
    f3PtpAccPortFlowPointThresholdValueHi     Unsigned32,
    f3PtpAccPortFlowPointThresholdMonValue    PerfCounter64
}

f3PtpAccPortFlowPointThresholdIndex OBJECT-TYPE
    SYNTAX     Integer32 (1..65535)
    MAX-ACCESS not-accessible 
    STATUS     current
    DESCRIPTION
        "An index that uniquely identifies an entry in the
        f3PtpAccPortFlowPointThresholdTable."
    ::= { f3PtpAccPortFlowPointThresholdEntry 1 }

f3PtpAccPortFlowPointThresholdInterval OBJECT-TYPE
    SYNTAX     CmPmIntervalType
    MAX-ACCESS read-only
    STATUS     current
    DESCRIPTION
        "The interval over which monitored value is
        sampled and compared with the specified threshold."
    ::= { f3PtpAccPortFlowPointThresholdEntry 2 }

f3PtpAccPortFlowPointThresholdVariable OBJECT-TYPE
    SYNTAX     VariablePointer
    MAX-ACCESS read-only
    STATUS     current
    DESCRIPTION
        "The object identifier of the particular variable to be
        sampled."
    ::= { f3PtpAccPortFlowPointThresholdEntry 3 }

f3PtpAccPortFlowPointThresholdValueLo OBJECT-TYPE
    SYNTAX     Unsigned32
    MAX-ACCESS read-write
    STATUS     current
    DESCRIPTION
        "Lower 32 bits of the threshold value."
    ::= { f3PtpAccPortFlowPointThresholdEntry 4 }

f3PtpAccPortFlowPointThresholdValueHi OBJECT-TYPE
    SYNTAX     Unsigned32
    MAX-ACCESS read-write
    STATUS     current
    DESCRIPTION
        "Higher 32 bits of the threshold value."
    ::= { f3PtpAccPortFlowPointThresholdEntry 5 }

f3PtpAccPortFlowPointThresholdMonValue OBJECT-TYPE
    SYNTAX     PerfCounter64
    MAX-ACCESS read-only
    STATUS     current
    DESCRIPTION
        "Monitored value corresponding to f3PtpAccPortFlowPointThresholdVariable."
    ::= { f3PtpAccPortFlowPointThresholdEntry 6 }

--
-- Network Port PTP Flow Point Current Statistics Table
--
f3PtpNetPortFlowPointStatsTable OBJECT-TYPE
    SYNTAX      SEQUENCE OF F3PtpNetPortFlowPointStatsEntry
    MAX-ACCESS  not-accessible
    STATUS      current
    DESCRIPTION
            "A collection of Network Port PTP Flow Point statistics.  
             These reflect the current data."
    ::= { f3PtpPerformanceObjects 4 }

f3PtpNetPortFlowPointStatsEntry OBJECT-TYPE
    SYNTAX      F3PtpNetPortFlowPointStatsEntry 
    MAX-ACCESS  not-accessible
    STATUS      current
    DESCRIPTION
            "A conceptual row in the f3PtpNetPortFlowPointStatsTable.
             Entries exist in this table for each Network Port Flow Point."
    INDEX { neIndex, shelfIndex, slotIndex, cmEthernetNetPortIndex, 
            f3PtpNetPortFlowPointIndex, f3PtpNetPortFlowPointStatsIndex }
    ::= { f3PtpNetPortFlowPointStatsTable 1 }

F3PtpNetPortFlowPointStatsEntry ::= SEQUENCE {
    f3PtpNetPortFlowPointStatsIndex                  Integer32,
    f3PtpNetPortFlowPointStatsIntervalType           CmPmIntervalType,
    f3PtpNetPortFlowPointStatsValid                  TruthValue,
    f3PtpNetPortFlowPointStatsAction                 CmPmBinAction,
    f3PtpNetPortFlowPointStatsAnnouncesRx            PerfCounter64,
    f3PtpNetPortFlowPointStatsAnnouncesTx            PerfCounter64,
    f3PtpNetPortFlowPointStatsSyncsRx                PerfCounter64,
    f3PtpNetPortFlowPointStatsSyncsTx                PerfCounter64,
    f3PtpNetPortFlowPointStatsFollowupsRx            PerfCounter64,
    f3PtpNetPortFlowPointStatsFollowupsTx            PerfCounter64,
    f3PtpNetPortFlowPointStatsDelayReqsRx            PerfCounter64,
    f3PtpNetPortFlowPointStatsDelayReqsTx            PerfCounter64,
    f3PtpNetPortFlowPointStatsDelayRspsRx            PerfCounter64,
    f3PtpNetPortFlowPointStatsDelayRspsTx            PerfCounter64,
    f3PtpNetPortFlowPointStatsPDelayReqsRx           PerfCounter64,
    f3PtpNetPortFlowPointStatsPDelayReqsTx           PerfCounter64,
    f3PtpNetPortFlowPointStatsPDelayRspsRx           PerfCounter64,
    f3PtpNetPortFlowPointStatsPDelayRspsTx           PerfCounter64,
    f3PtpNetPortFlowPointStatsPDelayRspFollowupsRx   PerfCounter64,
    f3PtpNetPortFlowPointStatsPDelayRspFollowupsTx   PerfCounter64,
    f3PtpNetPortFlowPointStatsSignalingRx            PerfCounter64,
    f3PtpNetPortFlowPointStatsSignalingTx            PerfCounter64,
    f3PtpNetPortFlowPointStatsMgmtFramesRx           PerfCounter64,
    f3PtpNetPortFlowPointStatsMgmtFramesTx           PerfCounter64,
    f3PtpNetPortFlowPointStatsPtpUnknownsRx          PerfCounter64,
    f3PtpNetPortFlowPointStatsPtpUnknownsTx          PerfCounter64,
    f3PtpNetPortFlowPointStatsAvgSyncResTime         Unsigned32,
    f3PtpNetPortFlowPointStatsMinSyncResTime         Unsigned32,
    f3PtpNetPortFlowPointStatsMaxSyncResTime         Unsigned32,
    f3PtpNetPortFlowPointStatsAvgDelayReqResTime     Unsigned32,
    f3PtpNetPortFlowPointStatsMinDelayReqResTime     Unsigned32,
    f3PtpNetPortFlowPointStatsMaxDelayReqResTime     Unsigned32,
    f3PtpNetPortFlowPointStatsMinPDelayReqResTime    Unsigned32,
    f3PtpNetPortFlowPointStatsMaxPDelayReqResTime    Unsigned32,
    f3PtpNetPortFlowPointStatsAvgPDelayReqResTime    Unsigned32,
    f3PtpNetPortFlowPointStatsMinPDelayRspResTime    Unsigned32,
    f3PtpNetPortFlowPointStatsMaxPDelayRspResTime    Unsigned32,
    f3PtpNetPortFlowPointStatsAvgPDelayRspResTime    Unsigned32,
    f3PtpNetPortFlowPointStatsDestMciNoMatchDiscards PerfCounter64,
    f3PtpNetPortFlowPointStatsTagNoMatchDiscards     PerfCounter64
}

f3PtpNetPortFlowPointStatsIndex OBJECT-TYPE
    SYNTAX      Integer32 (1..4)
    MAX-ACCESS  not-accessible
    STATUS      current
    DESCRIPTION
            "An arbitrary integer index value used to uniquely identify
            this Network Port PTP Flow Point statistics entry. 
            1 - 15min
            2 - 1day
            3 - rollover
            4 - 5min"
    ::= { f3PtpNetPortFlowPointStatsEntry 1 }

f3PtpNetPortFlowPointStatsIntervalType OBJECT-TYPE
    SYNTAX      CmPmIntervalType
    MAX-ACCESS  read-only
    STATUS      current
    DESCRIPTION
            "Indicates the type of collection, i.e. whether it is
             15 Min, 1 Day or rollover."
    ::= { f3PtpNetPortFlowPointStatsEntry 2 }

f3PtpNetPortFlowPointStatsValid OBJECT-TYPE
    SYNTAX      TruthValue
    MAX-ACCESS  read-only
    STATUS      current
    DESCRIPTION
            "Indicates the validity of the bin."
    ::= { f3PtpNetPortFlowPointStatsEntry 3 }

f3PtpNetPortFlowPointStatsAction OBJECT-TYPE
    SYNTAX      CmPmBinAction
    MAX-ACCESS  read-write
    STATUS      current
    DESCRIPTION
            "Allows the Manager to clear the bin."
    ::= { f3PtpNetPortFlowPointStatsEntry 4 }

f3PtpNetPortFlowPointStatsAnnouncesRx OBJECT-TYPE
     SYNTAX     PerfCounter64
     MAX-ACCESS read-only
     STATUS     current
     DESCRIPTION
         "Number of PTP Announce messages received on the PTP Flow Point."
     ::= { f3PtpNetPortFlowPointStatsEntry 5 }

f3PtpNetPortFlowPointStatsAnnouncesTx OBJECT-TYPE
     SYNTAX     PerfCounter64
     MAX-ACCESS read-only
     STATUS     current
     DESCRIPTION
         "Number of Announce Messages transmitted on the PTP Flow Point.
          This object is applicable for transparent clocks."
     ::= { f3PtpNetPortFlowPointStatsEntry 6 }

f3PtpNetPortFlowPointStatsSyncsRx OBJECT-TYPE
     SYNTAX     PerfCounter64
     MAX-ACCESS read-only
     STATUS     current
     DESCRIPTION
         "Number of Sync Messages received on the PTP Flow Point."
     ::= { f3PtpNetPortFlowPointStatsEntry 7 }

f3PtpNetPortFlowPointStatsSyncsTx OBJECT-TYPE
     SYNTAX     PerfCounter64
     MAX-ACCESS read-only
     STATUS     current
     DESCRIPTION
         "Number of Sync Messages transmitted on the PTP Flow Point.
          This object is applicable for transparent clocks."
     ::= { f3PtpNetPortFlowPointStatsEntry 8 }

f3PtpNetPortFlowPointStatsFollowupsRx OBJECT-TYPE
     SYNTAX     PerfCounter64
     MAX-ACCESS read-only
     STATUS     current
     DESCRIPTION
         "Number of Follow up Messages received on the PTP Flow Point."
     ::= { f3PtpNetPortFlowPointStatsEntry 9 }

f3PtpNetPortFlowPointStatsFollowupsTx OBJECT-TYPE
     SYNTAX     PerfCounter64
     MAX-ACCESS read-only
     STATUS     current
     DESCRIPTION
         "Number of Follow up Messages transmitted on the PTP Flow Point."
     ::= { f3PtpNetPortFlowPointStatsEntry 10 }

f3PtpNetPortFlowPointStatsDelayReqsRx OBJECT-TYPE
     SYNTAX     PerfCounter64
     MAX-ACCESS read-only
     STATUS     current
     DESCRIPTION
         "Number of Delay Request Messages received on the PTP Flow Point."
     ::= { f3PtpNetPortFlowPointStatsEntry 11 }

f3PtpNetPortFlowPointStatsDelayReqsTx OBJECT-TYPE
     SYNTAX     PerfCounter64
     MAX-ACCESS read-only
     STATUS     current
     DESCRIPTION
         "Number of Delay Request Messages transmitted on the PTP Flow Point."
     ::= { f3PtpNetPortFlowPointStatsEntry 12 }

f3PtpNetPortFlowPointStatsDelayRspsRx OBJECT-TYPE
     SYNTAX     PerfCounter64
     MAX-ACCESS read-only
     STATUS     current
     DESCRIPTION
         "Number of Delay Response Messages received on the PTP Flow Point."
     ::= { f3PtpNetPortFlowPointStatsEntry 13 }

f3PtpNetPortFlowPointStatsDelayRspsTx OBJECT-TYPE
     SYNTAX     PerfCounter64
     MAX-ACCESS read-only
     STATUS     current
     DESCRIPTION
         "Number of Delay Response Messages transmitted on the PTP Flow Point."
     ::= { f3PtpNetPortFlowPointStatsEntry 14 }

f3PtpNetPortFlowPointStatsPDelayReqsRx OBJECT-TYPE
     SYNTAX     PerfCounter64
     MAX-ACCESS read-only
     STATUS     current
     DESCRIPTION
         "Number of Peer Delay Request Messages received on the PTP Flow Point."
     ::= { f3PtpNetPortFlowPointStatsEntry 15 }

f3PtpNetPortFlowPointStatsPDelayReqsTx OBJECT-TYPE
     SYNTAX     PerfCounter64
     MAX-ACCESS read-only
     STATUS     current
     DESCRIPTION
         "Number of Peer Delay Request Messages transmitted on the PTP Flow Point."
     ::= { f3PtpNetPortFlowPointStatsEntry 16 }

f3PtpNetPortFlowPointStatsPDelayRspsRx OBJECT-TYPE
     SYNTAX     PerfCounter64
     MAX-ACCESS read-only
     STATUS     current
     DESCRIPTION
         "Number of Peer Delay Response Messages received on the PTP Flow Point."
     ::= { f3PtpNetPortFlowPointStatsEntry 17 }

f3PtpNetPortFlowPointStatsPDelayRspsTx OBJECT-TYPE
     SYNTAX     PerfCounter64
     MAX-ACCESS read-only
     STATUS     current
     DESCRIPTION
         "Number of Peer Delay Response Messages transmitted on the PTP Flow Point."
     ::= { f3PtpNetPortFlowPointStatsEntry 18 }

f3PtpNetPortFlowPointStatsPDelayRspFollowupsRx OBJECT-TYPE
     SYNTAX     PerfCounter64
     MAX-ACCESS read-only
     STATUS     current
     DESCRIPTION
         "Number of Peer Delay Response Followup Messages received on the PTP Flow Point."
     ::= { f3PtpNetPortFlowPointStatsEntry 19 }

f3PtpNetPortFlowPointStatsPDelayRspFollowupsTx OBJECT-TYPE
     SYNTAX     PerfCounter64
     MAX-ACCESS read-only
     STATUS     current
     DESCRIPTION
         "Number of Peer Delay Response Followup Messages transmitted on the PTP Flow Point."
     ::= { f3PtpNetPortFlowPointStatsEntry 20 }

f3PtpNetPortFlowPointStatsSignalingRx OBJECT-TYPE
     SYNTAX     PerfCounter64
     MAX-ACCESS read-only
     STATUS     current
     DESCRIPTION
         "Number of PTP Signaling Messages received on the PTP Flow Point."
     ::= { f3PtpNetPortFlowPointStatsEntry 21 }

f3PtpNetPortFlowPointStatsSignalingTx OBJECT-TYPE
     SYNTAX     PerfCounter64
     MAX-ACCESS read-only
     STATUS     current
     DESCRIPTION
         "Number of PTP Signaling Messages Messages transmitted on the PTP Flow Point."
     ::= { f3PtpNetPortFlowPointStatsEntry 22 }

f3PtpNetPortFlowPointStatsMgmtFramesRx OBJECT-TYPE
     SYNTAX     PerfCounter64
     MAX-ACCESS read-only
     STATUS     current
     DESCRIPTION
         "Number of PTP Management Frames received on the PTP Flow Point."
     ::= { f3PtpNetPortFlowPointStatsEntry 23 }

f3PtpNetPortFlowPointStatsMgmtFramesTx OBJECT-TYPE
     SYNTAX     PerfCounter64
     MAX-ACCESS read-only
     STATUS     current
     DESCRIPTION
         "Number of PTP Management Frames Messages transmitted on the PTP Flow Point."
     ::= { f3PtpNetPortFlowPointStatsEntry 24 }

f3PtpNetPortFlowPointStatsPtpUnknownsRx OBJECT-TYPE
     SYNTAX     PerfCounter64
     MAX-ACCESS read-only
     STATUS     current
     DESCRIPTION
         "Number of Unknown PTP Messages received on the PTP Flow Point."
     ::= { f3PtpNetPortFlowPointStatsEntry 25 }

f3PtpNetPortFlowPointStatsPtpUnknownsTx OBJECT-TYPE
     SYNTAX     PerfCounter64
     MAX-ACCESS read-only
     STATUS     current
     DESCRIPTION
         "Number of Unknown PTP Messages transmitted on the PTP Flow Point."
     ::= { f3PtpNetPortFlowPointStatsEntry 26 }

f3PtpNetPortFlowPointStatsAvgSyncResTime OBJECT-TYPE
     SYNTAX     Unsigned32
     MAX-ACCESS read-only
     STATUS     deprecated
     DESCRIPTION
         "The average residence time for PTP Sync messages."
     ::= { f3PtpNetPortFlowPointStatsEntry 27 }

f3PtpNetPortFlowPointStatsMinSyncResTime OBJECT-TYPE
     SYNTAX     Unsigned32
     MAX-ACCESS read-only
     STATUS     deprecated
     DESCRIPTION
         "The minimum residence time for PTP Sync messages."
     ::= { f3PtpNetPortFlowPointStatsEntry 28 }

f3PtpNetPortFlowPointStatsMaxSyncResTime OBJECT-TYPE
     SYNTAX     Unsigned32
     MAX-ACCESS read-only
     STATUS     deprecated
     DESCRIPTION
         "The maximum residence time for PTP Sync messages."
     ::= { f3PtpNetPortFlowPointStatsEntry 29 }

f3PtpNetPortFlowPointStatsAvgDelayReqResTime OBJECT-TYPE
     SYNTAX     Unsigned32
     MAX-ACCESS read-only
     STATUS     deprecated
     DESCRIPTION
         "The average residence time for PTP Delay Request messages."
     ::= { f3PtpNetPortFlowPointStatsEntry 30 }

f3PtpNetPortFlowPointStatsMinDelayReqResTime OBJECT-TYPE
     SYNTAX     Unsigned32
     MAX-ACCESS read-only
     STATUS     deprecated
     DESCRIPTION
         "The minimum residence time for PTP Delay Request messages."
     ::= { f3PtpNetPortFlowPointStatsEntry 31 }

f3PtpNetPortFlowPointStatsMaxDelayReqResTime OBJECT-TYPE
     SYNTAX     Unsigned32
     MAX-ACCESS read-only
     STATUS     deprecated
     DESCRIPTION
         "The maximum residence time for PTP Delay Request messages."
     ::= { f3PtpNetPortFlowPointStatsEntry 32 }

f3PtpNetPortFlowPointStatsMinPDelayReqResTime OBJECT-TYPE
     SYNTAX     Unsigned32
     MAX-ACCESS read-only
     STATUS     deprecated
     DESCRIPTION
         "The minimum residence time for PTP Peer Delay Request messages."
     ::= { f3PtpNetPortFlowPointStatsEntry 33 }

f3PtpNetPortFlowPointStatsMaxPDelayReqResTime OBJECT-TYPE
     SYNTAX     Unsigned32
     MAX-ACCESS read-only
     STATUS     deprecated
     DESCRIPTION
         "The maximum residence time for PTP Peer Delay Request messages."
     ::= { f3PtpNetPortFlowPointStatsEntry 34 }

f3PtpNetPortFlowPointStatsAvgPDelayReqResTime OBJECT-TYPE
     SYNTAX     Unsigned32
     MAX-ACCESS read-only
     STATUS     deprecated
     DESCRIPTION
         "The average residence time for PTP Peer Delay Request messages."
     ::= { f3PtpNetPortFlowPointStatsEntry 35 }

f3PtpNetPortFlowPointStatsMinPDelayRspResTime OBJECT-TYPE
     SYNTAX     Unsigned32
     MAX-ACCESS read-only
     STATUS     deprecated
     DESCRIPTION
         "The minimum residence time for PTP Peer Delay Response messages."
     ::= { f3PtpNetPortFlowPointStatsEntry 36 }

f3PtpNetPortFlowPointStatsMaxPDelayRspResTime OBJECT-TYPE
     SYNTAX     Unsigned32
     MAX-ACCESS read-only
     STATUS     deprecated
     DESCRIPTION
         "The maximum residence time for PTP Peer Delay Response messages."
     ::= { f3PtpNetPortFlowPointStatsEntry 37 }

f3PtpNetPortFlowPointStatsAvgPDelayRspResTime OBJECT-TYPE
     SYNTAX     Unsigned32
     MAX-ACCESS read-only
     STATUS     deprecated
     DESCRIPTION
         "The average residence time for PTP Peer Delay Response messages."
     ::= { f3PtpNetPortFlowPointStatsEntry 38 }

f3PtpNetPortFlowPointStatsDestMciNoMatchDiscards OBJECT-TYPE
     SYNTAX     PerfCounter64
     MAX-ACCESS read-write
     STATUS     current
     DESCRIPTION
         "The dest MCI no match discards messages."
     ::= { f3PtpNetPortFlowPointStatsEntry 39 }

f3PtpNetPortFlowPointStatsTagNoMatchDiscards OBJECT-TYPE
     SYNTAX     PerfCounter64
     MAX-ACCESS read-write
     STATUS     current
     DESCRIPTION
         "The tag no match discards messages."
     ::= { f3PtpNetPortFlowPointStatsEntry 40 }

--
-- Network Port PTP Flow Point History Table
--
f3PtpNetPortFlowPointHistoryTable OBJECT-TYPE
    SYNTAX      SEQUENCE OF F3PtpNetPortFlowPointHistoryEntry
    MAX-ACCESS  not-accessible
    STATUS      current
    DESCRIPTION
            "A collection of Network Port PTP Flow Point history statistics.  
             These reflect the history data."
    ::= { f3PtpPerformanceObjects 5 }

f3PtpNetPortFlowPointHistoryEntry OBJECT-TYPE
    SYNTAX      F3PtpNetPortFlowPointHistoryEntry 
    MAX-ACCESS  not-accessible
    STATUS      current
    DESCRIPTION
            "A conceptual row in the f3PtpNetPortFlowPointHistoryTable.
             Entries exist in this table for each Network Port Flow Point."
    INDEX { neIndex, shelfIndex, slotIndex, cmEthernetNetPortIndex, 
            f3PtpNetPortFlowPointIndex, f3PtpNetPortFlowPointStatsIndex, f3PtpNetPortFlowPointHistoryIndex }
    ::= { f3PtpNetPortFlowPointHistoryTable 1 }

F3PtpNetPortFlowPointHistoryEntry ::= SEQUENCE {
    f3PtpNetPortFlowPointHistoryIndex                  Integer32,
    f3PtpNetPortFlowPointHistoryTime                   DateAndTime,
    f3PtpNetPortFlowPointHistoryValid                  TruthValue,
    f3PtpNetPortFlowPointHistoryAction                 CmPmBinAction,
    f3PtpNetPortFlowPointHistoryAnnouncesRx            PerfCounter64,
    f3PtpNetPortFlowPointHistoryAnnouncesTx            PerfCounter64,
    f3PtpNetPortFlowPointHistorySyncsRx                PerfCounter64,
    f3PtpNetPortFlowPointHistorySyncsTx                PerfCounter64,
    f3PtpNetPortFlowPointHistoryFollowupsRx            PerfCounter64,
    f3PtpNetPortFlowPointHistoryFollowupsTx            PerfCounter64,
    f3PtpNetPortFlowPointHistoryDelayReqsRx            PerfCounter64,
    f3PtpNetPortFlowPointHistoryDelayReqsTx            PerfCounter64,
    f3PtpNetPortFlowPointHistoryDelayRspsRx            PerfCounter64,
    f3PtpNetPortFlowPointHistoryDelayRspsTx            PerfCounter64,
    f3PtpNetPortFlowPointHistoryPDelayReqsRx           PerfCounter64,
    f3PtpNetPortFlowPointHistoryPDelayReqsTx           PerfCounter64,
    f3PtpNetPortFlowPointHistoryPDelayRspsRx           PerfCounter64,
    f3PtpNetPortFlowPointHistoryPDelayRspsTx           PerfCounter64,
    f3PtpNetPortFlowPointHistoryPDelayRspFollowupsRx   PerfCounter64,
    f3PtpNetPortFlowPointHistoryPDelayRspFollowupsTx   PerfCounter64,
    f3PtpNetPortFlowPointHistorySignalingRx            PerfCounter64,
    f3PtpNetPortFlowPointHistorySignalingTx            PerfCounter64,
    f3PtpNetPortFlowPointHistoryMgmtFramesRx           PerfCounter64,
    f3PtpNetPortFlowPointHistoryMgmtFramesTx           PerfCounter64,
    f3PtpNetPortFlowPointHistoryPtpUnknownsRx          PerfCounter64,
    f3PtpNetPortFlowPointHistoryPtpUnknownsTx          PerfCounter64,
    f3PtpNetPortFlowPointHistoryAvgSyncResTime         Unsigned32,
    f3PtpNetPortFlowPointHistoryMinSyncResTime         Unsigned32,
    f3PtpNetPortFlowPointHistoryMaxSyncResTime         Unsigned32,
    f3PtpNetPortFlowPointHistoryAvgDelayReqResTime     Unsigned32,
    f3PtpNetPortFlowPointHistoryMinDelayReqResTime     Unsigned32,
    f3PtpNetPortFlowPointHistoryMaxDelayReqResTime     Unsigned32,
    f3PtpNetPortFlowPointHistoryMinPDelayReqResTime    Unsigned32,
    f3PtpNetPortFlowPointHistoryMaxPDelayReqResTime    Unsigned32,
    f3PtpNetPortFlowPointHistoryAvgPDelayReqResTime    Unsigned32,
    f3PtpNetPortFlowPointHistoryMinPDelayRspResTime    Unsigned32,
    f3PtpNetPortFlowPointHistoryMaxPDelayRspResTime    Unsigned32,
    f3PtpNetPortFlowPointHistoryAvgPDelayRspResTime    Unsigned32,
    f3PtpNetPortFlowPointHistoryDestMciNoMatchDiscards PerfCounter64,
    f3PtpNetPortFlowPointHistoryTagNoMatchDiscards     PerfCounter64
}

f3PtpNetPortFlowPointHistoryIndex OBJECT-TYPE
    SYNTAX      Integer32 (1..32)
    MAX-ACCESS  not-accessible
    STATUS      current
    DESCRIPTION
            "An arbitrary integer index value used to uniquely identify
            this Ethernet Network Port PTP Flow point PM history entry."
    ::= { f3PtpNetPortFlowPointHistoryEntry 1 }

f3PtpNetPortFlowPointHistoryTime OBJECT-TYPE
    SYNTAX      DateAndTime
    MAX-ACCESS  read-only
    STATUS      current
    DESCRIPTION
            "Indicates the time of history bin creation." 
    ::= { f3PtpNetPortFlowPointHistoryEntry 2 }

f3PtpNetPortFlowPointHistoryValid OBJECT-TYPE
    SYNTAX      TruthValue
    MAX-ACCESS  read-only
    STATUS      current
    DESCRIPTION
            "Indicates the validity of the bin."
    ::= { f3PtpNetPortFlowPointHistoryEntry 3 }

f3PtpNetPortFlowPointHistoryAction OBJECT-TYPE
    SYNTAX      CmPmBinAction
    MAX-ACCESS  read-write
    STATUS      current
    DESCRIPTION
            "Allows the Manager to clear the bin."
    ::= { f3PtpNetPortFlowPointHistoryEntry 4 }

f3PtpNetPortFlowPointHistoryAnnouncesRx OBJECT-TYPE
     SYNTAX     PerfCounter64
     MAX-ACCESS read-only
     STATUS     current
     DESCRIPTION
         "Number of PTP Announce messages received on the PTP Flow Point."
     ::= { f3PtpNetPortFlowPointHistoryEntry 5 }

f3PtpNetPortFlowPointHistoryAnnouncesTx OBJECT-TYPE
     SYNTAX     PerfCounter64
     MAX-ACCESS read-only
     STATUS     current
     DESCRIPTION
         "Number of Announce Messages transmitted on the PTP Flow Point.
          This object is applicable for transparent clocks."
     ::= { f3PtpNetPortFlowPointHistoryEntry 6 }

f3PtpNetPortFlowPointHistorySyncsRx OBJECT-TYPE
     SYNTAX     PerfCounter64
     MAX-ACCESS read-only
     STATUS     current
     DESCRIPTION
         "Number of Sync Messages received on the PTP Flow Point."
     ::= { f3PtpNetPortFlowPointHistoryEntry 7 }

f3PtpNetPortFlowPointHistorySyncsTx OBJECT-TYPE
     SYNTAX     PerfCounter64
     MAX-ACCESS read-only
     STATUS     current
     DESCRIPTION
         "Number of Sync Messages transmitted on the PTP Flow Point.
          This object is applicable for transparent clocks."
     ::= { f3PtpNetPortFlowPointHistoryEntry 8 }

f3PtpNetPortFlowPointHistoryFollowupsRx OBJECT-TYPE
     SYNTAX     PerfCounter64
     MAX-ACCESS read-only
     STATUS     current
     DESCRIPTION
         "Number of Follow up Messages received on the PTP Flow Point."
     ::= { f3PtpNetPortFlowPointHistoryEntry 9 }

f3PtpNetPortFlowPointHistoryFollowupsTx OBJECT-TYPE
     SYNTAX     PerfCounter64
     MAX-ACCESS read-only
     STATUS     current
     DESCRIPTION
         "Number of Follow up Messages transmitted on the PTP Flow Point."
     ::= { f3PtpNetPortFlowPointHistoryEntry 10 }

f3PtpNetPortFlowPointHistoryDelayReqsRx OBJECT-TYPE
     SYNTAX     PerfCounter64
     MAX-ACCESS read-only
     STATUS     current
     DESCRIPTION
         "Number of Delay Request Messages received on the PTP Flow Point."
     ::= { f3PtpNetPortFlowPointHistoryEntry 11 }

f3PtpNetPortFlowPointHistoryDelayReqsTx OBJECT-TYPE
     SYNTAX     PerfCounter64
     MAX-ACCESS read-only
     STATUS     current
     DESCRIPTION
         "Number of Delay Request Messages transmitted on the PTP Flow Point."
     ::= { f3PtpNetPortFlowPointHistoryEntry 12 }

f3PtpNetPortFlowPointHistoryDelayRspsRx OBJECT-TYPE
     SYNTAX     PerfCounter64
     MAX-ACCESS read-only
     STATUS     current
     DESCRIPTION
         "Number of Delay Response Messages received on the PTP Flow Point."
     ::= { f3PtpNetPortFlowPointHistoryEntry 13 }

f3PtpNetPortFlowPointHistoryDelayRspsTx OBJECT-TYPE
     SYNTAX     PerfCounter64
     MAX-ACCESS read-only
     STATUS     current
     DESCRIPTION
         "Number of Delay Response Messages transmitted on the PTP Flow Point."
     ::= { f3PtpNetPortFlowPointHistoryEntry 14 }

f3PtpNetPortFlowPointHistoryPDelayReqsRx OBJECT-TYPE
     SYNTAX     PerfCounter64
     MAX-ACCESS read-only
     STATUS     current
     DESCRIPTION
         "Number of Peer Delay Request Messages received on the PTP Flow Point."
     ::= { f3PtpNetPortFlowPointHistoryEntry 15 }

f3PtpNetPortFlowPointHistoryPDelayReqsTx OBJECT-TYPE
     SYNTAX     PerfCounter64
     MAX-ACCESS read-only
     STATUS     current
     DESCRIPTION
         "Number of Peer Delay Request Messages transmitted on the PTP Flow Point."
     ::= { f3PtpNetPortFlowPointHistoryEntry 16 }

f3PtpNetPortFlowPointHistoryPDelayRspsRx OBJECT-TYPE
     SYNTAX     PerfCounter64
     MAX-ACCESS read-only
     STATUS     current
     DESCRIPTION
         "Number of Peer Delay Response Messages received on the PTP Flow Point."
     ::= { f3PtpNetPortFlowPointHistoryEntry 17 }

f3PtpNetPortFlowPointHistoryPDelayRspsTx OBJECT-TYPE
     SYNTAX     PerfCounter64
     MAX-ACCESS read-only
     STATUS     current
     DESCRIPTION
         "Number of Peer Delay Response Messages transmitted on the PTP Flow Point."
     ::= { f3PtpNetPortFlowPointHistoryEntry 18 }

f3PtpNetPortFlowPointHistoryPDelayRspFollowupsRx OBJECT-TYPE
     SYNTAX     PerfCounter64
     MAX-ACCESS read-only
     STATUS     current
     DESCRIPTION
         "Number of Peer Delay Response Followup Messages received on the PTP Flow Point."
     ::= { f3PtpNetPortFlowPointHistoryEntry 19 }

f3PtpNetPortFlowPointHistoryPDelayRspFollowupsTx OBJECT-TYPE
     SYNTAX     PerfCounter64
     MAX-ACCESS read-only
     STATUS     current
     DESCRIPTION
         "Number of Peer Delay Response Followup Messages transmitted on the PTP Flow Point."
     ::= { f3PtpNetPortFlowPointHistoryEntry 20 }

f3PtpNetPortFlowPointHistorySignalingRx OBJECT-TYPE
     SYNTAX     PerfCounter64
     MAX-ACCESS read-only
     STATUS     current
     DESCRIPTION
         "Number of PTP Signaling Messages received on the PTP Flow Point."
     ::= { f3PtpNetPortFlowPointHistoryEntry 21 }

f3PtpNetPortFlowPointHistorySignalingTx OBJECT-TYPE
     SYNTAX     PerfCounter64
     MAX-ACCESS read-only
     STATUS     current
     DESCRIPTION
         "Number of PTP Signaling Messages Messages transmitted on the PTP Flow Point."
     ::= { f3PtpNetPortFlowPointHistoryEntry 22 }

f3PtpNetPortFlowPointHistoryMgmtFramesRx OBJECT-TYPE
     SYNTAX     PerfCounter64
     MAX-ACCESS read-only
     STATUS     current
     DESCRIPTION
         "Number of PTP Management Frames received on the PTP Flow Point."
     ::= { f3PtpNetPortFlowPointHistoryEntry 23 }

f3PtpNetPortFlowPointHistoryMgmtFramesTx OBJECT-TYPE
     SYNTAX     PerfCounter64
     MAX-ACCESS read-only
     STATUS     current
     DESCRIPTION
         "Number of PTP Management Frames Messages transmitted on the PTP Flow Point."
     ::= { f3PtpNetPortFlowPointHistoryEntry 24 }

f3PtpNetPortFlowPointHistoryPtpUnknownsRx OBJECT-TYPE
     SYNTAX     PerfCounter64
     MAX-ACCESS read-only
     STATUS     current
     DESCRIPTION
         "Number of Unknown PTP Messages received on the PTP Flow Point."
     ::= { f3PtpNetPortFlowPointHistoryEntry 25 }

f3PtpNetPortFlowPointHistoryPtpUnknownsTx OBJECT-TYPE
     SYNTAX     PerfCounter64
     MAX-ACCESS read-only
     STATUS     current
     DESCRIPTION
         "Number of Unknown PTP Messages transmitted on the PTP Flow Point."
     ::= { f3PtpNetPortFlowPointHistoryEntry 26 }

f3PtpNetPortFlowPointHistoryAvgSyncResTime OBJECT-TYPE
     SYNTAX     Unsigned32
     MAX-ACCESS read-only
     STATUS     deprecated
     DESCRIPTION
         "The average residence time for PTP Sync messages."
     ::= { f3PtpNetPortFlowPointHistoryEntry 27 }

f3PtpNetPortFlowPointHistoryMinSyncResTime OBJECT-TYPE
     SYNTAX     Unsigned32
     MAX-ACCESS read-only
     STATUS     deprecated
     DESCRIPTION
         "The minimum residence time for PTP Sync messages."
     ::= { f3PtpNetPortFlowPointHistoryEntry 28 }

f3PtpNetPortFlowPointHistoryMaxSyncResTime OBJECT-TYPE
     SYNTAX     Unsigned32
     MAX-ACCESS read-only
     STATUS     deprecated
     DESCRIPTION
         "The maximum residence time for PTP Sync messages."
     ::= { f3PtpNetPortFlowPointHistoryEntry 29 }

f3PtpNetPortFlowPointHistoryAvgDelayReqResTime OBJECT-TYPE
     SYNTAX     Unsigned32
     MAX-ACCESS read-only
     STATUS     deprecated
     DESCRIPTION
         "The average residence time for PTP Delay Request messages."
     ::= { f3PtpNetPortFlowPointHistoryEntry 30 }

f3PtpNetPortFlowPointHistoryMinDelayReqResTime OBJECT-TYPE
     SYNTAX     Unsigned32
     MAX-ACCESS read-only
     STATUS     deprecated
     DESCRIPTION
         "The minimum residence time for PTP Delay Request messages."
     ::= { f3PtpNetPortFlowPointHistoryEntry 31 }

f3PtpNetPortFlowPointHistoryMaxDelayReqResTime OBJECT-TYPE
     SYNTAX     Unsigned32
     MAX-ACCESS read-only
     STATUS     deprecated
     DESCRIPTION
         "The maximum residence time for PTP Delay Request messages."
     ::= { f3PtpNetPortFlowPointHistoryEntry 32 }

f3PtpNetPortFlowPointHistoryMinPDelayReqResTime OBJECT-TYPE
     SYNTAX     Unsigned32
     MAX-ACCESS read-only
     STATUS     deprecated
     DESCRIPTION
         "The minimum residence time for PTP Peer Delay Request messages."
     ::= { f3PtpNetPortFlowPointHistoryEntry 33 }

f3PtpNetPortFlowPointHistoryMaxPDelayReqResTime OBJECT-TYPE
     SYNTAX     Unsigned32
     MAX-ACCESS read-only
     STATUS     deprecated
     DESCRIPTION
         "The maximum residence time for PTP Peer Delay Request messages."
     ::= { f3PtpNetPortFlowPointHistoryEntry 34 }

f3PtpNetPortFlowPointHistoryAvgPDelayReqResTime OBJECT-TYPE
     SYNTAX     Unsigned32
     MAX-ACCESS read-only
     STATUS     deprecated
     DESCRIPTION
         "The average residence time for PTP Peer Delay Request messages."
     ::= { f3PtpNetPortFlowPointHistoryEntry 35 }

f3PtpNetPortFlowPointHistoryMinPDelayRspResTime OBJECT-TYPE
     SYNTAX     Unsigned32
     MAX-ACCESS read-only
     STATUS     deprecated
     DESCRIPTION
         "The minimum residence time for PTP Peer Delay Response messages."
     ::= { f3PtpNetPortFlowPointHistoryEntry 36 }

f3PtpNetPortFlowPointHistoryMaxPDelayRspResTime OBJECT-TYPE
     SYNTAX     Unsigned32
     MAX-ACCESS read-only
     STATUS     deprecated
     DESCRIPTION
         "The maximum residence time for PTP Peer Delay Response messages."
     ::= { f3PtpNetPortFlowPointHistoryEntry 37 }

f3PtpNetPortFlowPointHistoryAvgPDelayRspResTime OBJECT-TYPE
     SYNTAX     Unsigned32
     MAX-ACCESS read-only
     STATUS     deprecated
     DESCRIPTION
         "The average residence time for PTP Peer Delay Response messages."
     ::= { f3PtpNetPortFlowPointHistoryEntry 38 }

f3PtpNetPortFlowPointHistoryDestMciNoMatchDiscards OBJECT-TYPE
     SYNTAX     PerfCounter64
     MAX-ACCESS read-write
     STATUS     current
     DESCRIPTION
         "The dest MCI no match discards messages."
     ::= { f3PtpNetPortFlowPointHistoryEntry 39 }

f3PtpNetPortFlowPointHistoryTagNoMatchDiscards OBJECT-TYPE
     SYNTAX     PerfCounter64
     MAX-ACCESS read-write
     STATUS     current
     DESCRIPTION
         "The Tag no match discards messages."
     ::= { f3PtpNetPortFlowPointHistoryEntry 40 }

--
-- Network Port PTP Flow Point Threshold Table
--
f3PtpNetPortFlowPointThresholdTable OBJECT-TYPE
    SYNTAX      SEQUENCE OF F3PtpNetPortFlowPointThresholdEntry
    MAX-ACCESS  not-accessible
    STATUS      current
    DESCRIPTION
            "A table of entries that allow manageability of Access Port PTP Flow Point
             Thresholds."
    ::= { f3PtpPerformanceObjects 6 }

f3PtpNetPortFlowPointThresholdEntry OBJECT-TYPE
    SYNTAX      F3PtpNetPortFlowPointThresholdEntry
    MAX-ACCESS  not-accessible
    STATUS      current
    DESCRIPTION
            "A conceptual row in the f3PtpNetPortFlowPointThresholdTable."
    INDEX { neIndex, shelfIndex, slotIndex, cmEthernetNetPortIndex, 
            f3PtpNetPortFlowPointIndex, f3PtpNetPortFlowPointStatsIndex, 
            f3PtpNetPortFlowPointThresholdIndex }
    ::= { f3PtpNetPortFlowPointThresholdTable 1 }

F3PtpNetPortFlowPointThresholdEntry ::= SEQUENCE {
    f3PtpNetPortFlowPointThresholdIndex       Integer32,
    f3PtpNetPortFlowPointThresholdInterval    CmPmIntervalType,
    f3PtpNetPortFlowPointThresholdVariable    VariablePointer,
    f3PtpNetPortFlowPointThresholdValueLo     Unsigned32,
    f3PtpNetPortFlowPointThresholdValueHi     Unsigned32,
    f3PtpNetPortFlowPointThresholdMonValue    PerfCounter64
}

f3PtpNetPortFlowPointThresholdIndex OBJECT-TYPE
    SYNTAX     Integer32 (1..65535)
    MAX-ACCESS not-accessible
    STATUS     current
    DESCRIPTION
        "An index that uniquely identifies an entry in the
        f3PtpNetPortFlowPointThresholdTable."
    ::= { f3PtpNetPortFlowPointThresholdEntry 1 }

f3PtpNetPortFlowPointThresholdInterval OBJECT-TYPE
    SYNTAX     CmPmIntervalType
    MAX-ACCESS read-only
    STATUS     current
    DESCRIPTION
        "The interval over which monitored value is
        sampled and compared with the specified threshold."
    ::= { f3PtpNetPortFlowPointThresholdEntry 2 }

f3PtpNetPortFlowPointThresholdVariable OBJECT-TYPE
    SYNTAX     VariablePointer
    MAX-ACCESS read-only
    STATUS     current
    DESCRIPTION
        "The object identifier of the particular variable to be
        sampled."
    ::= { f3PtpNetPortFlowPointThresholdEntry 3 }

f3PtpNetPortFlowPointThresholdValueLo OBJECT-TYPE
    SYNTAX     Unsigned32
    MAX-ACCESS read-write
    STATUS     current
    DESCRIPTION
        "Lower 32 bits of the threshold value."
    ::= { f3PtpNetPortFlowPointThresholdEntry 4 }

f3PtpNetPortFlowPointThresholdValueHi OBJECT-TYPE
    SYNTAX     Unsigned32
    MAX-ACCESS read-write
    STATUS     current
    DESCRIPTION
        "Higher 32 bits of the threshold value."
    ::= { f3PtpNetPortFlowPointThresholdEntry 5 }

f3PtpNetPortFlowPointThresholdMonValue OBJECT-TYPE
    SYNTAX     PerfCounter64
    MAX-ACCESS read-only
    STATUS     current
    DESCRIPTION
        "Monitored value corresponding to f3PtpNetPortFlowPointThresholdVariable."
    ::= { f3PtpNetPortFlowPointThresholdEntry 6 }

--
-- Slave Only Ordinary Clock Current Statistics Table
--
f3PtpSOOCStatsTable OBJECT-TYPE
    SYNTAX      SEQUENCE OF F3PtpSOOCStatsEntry
    MAX-ACCESS  not-accessible
    STATUS      current
    DESCRIPTION
            "A collection of Slave Only Ordinary Clock related statistics.  
             These reflect the current data."
    ::= { f3PtpPerformanceObjects 7 }

f3PtpSOOCStatsEntry OBJECT-TYPE
    SYNTAX      F3PtpSOOCStatsEntry 
    MAX-ACCESS  not-accessible
    STATUS      current
    DESCRIPTION
            "A conceptual row in the f3PtpSOOCStatsTable.
             Entries exist in this table for each Slave Only Ordinary Clock."
    INDEX { neIndex, f3PtpTSIndex,  
                     f3PtpSOOCIndex, f3PtpSOOCStatsIndex }
    ::= { f3PtpSOOCStatsTable 1 }

F3PtpSOOCStatsEntry ::= SEQUENCE {
    f3PtpSOOCStatsIndex                       Integer32,
    f3PtpSOOCStatsIntervalType                CmPmIntervalType,
    f3PtpSOOCStatsValid                       TruthValue,
    f3PtpSOOCStatsAction                      CmPmBinAction,
    f3PtpSOOCStatsMinOffsetFromMaster         ScaledNanoseconds,
    f3PtpSOOCStatsMaxOffsetFromMaster         ScaledNanoseconds,
    f3PtpSOOCStatsAvgOffsetFromMaster         ScaledNanoseconds,
    f3PtpSOOCStatsMinMeanPathDelay            ScaledNanoseconds,
    f3PtpSOOCStatsMaxMeanPathDelay            ScaledNanoseconds,
    f3PtpSOOCStatsAvgMeanPathDelay            ScaledNanoseconds,
    f3PtpSOOCStatsMinSyncPathDelay            ScaledNanoseconds,
    f3PtpSOOCStatsMaxSyncPathDelay            ScaledNanoseconds,
    f3PtpSOOCStatsAvgSyncPathDelay            ScaledNanoseconds,
    f3PtpSOOCStatsMinSyncPDV                  ScaledNanoseconds,
    f3PtpSOOCStatsMaxSyncPDV                  ScaledNanoseconds,
    f3PtpSOOCStatsAvgSyncPDV                  ScaledNanoseconds,
    f3PtpSOOCStatsMgmtMsgsDiscarded           PerfCounter64,
    f3PtpSOOCStatsInvalidMsgLenDiscards       PerfCounter64,
    f3PtpSOOCStatsUnknownMasterDiscards       PerfCounter64,
    f3PtpSOOCStatsUnknownDomainDiscards       PerfCounter64,
    f3PtpSOOCStatsMulticastAnnounceDiscards   PerfCounter64,
    f3PtpSOOCStatsOutOfSeqAnnounceMsgs        PerfCounter64,
    f3PtpSOOCStatsMulticastSyncDiscards       PerfCounter64,
    f3PtpSOOCStatsTwoStepSyncDiscards         PerfCounter64,
    f3PtpSOOCStatsFollowupDiscards            PerfCounter64,
    f3PtpSOOCStatsDelayReqDiscards            PerfCounter64,
    f3PtpSOOCStatsPDelayReqDiscards           PerfCounter64,
    f3PtpSOOCStatsPDelayRspDiscards           PerfCounter64,
    f3PtpSOOCStatsPDelayFollowupDiscards      PerfCounter64,
    f3PtpSOOCStatsInvalidTLVLenDiscards       PerfCounter64,
    f3PtpSOOCStatsInvalidTLVTypeDiscards      PerfCounter64,
    f3PtpSOOCStatsMaxFwdFlowWeight            Integer32,
    f3PtpSOOCStatsAvgFwdFlowWeight            Integer32,
    f3PtpSOOCStatsMinRevFlowWeight            Integer32,
    f3PtpSOOCStatsMaxRevFlowWeight            Integer32,
    f3PtpSOOCStatsAvgRevFlowWeight            Integer32,
    f3PtpSOOCStatsNumClockRecTransients       Unsigned32
}

f3PtpSOOCStatsIndex OBJECT-TYPE
    SYNTAX      Integer32 (1..4)
    MAX-ACCESS  not-accessible
    STATUS      current
    DESCRIPTION
            "An arbitrary integer index value used to uniquely identify
            this Slave Only Ordinary Clock statistics entry. 
            1 - 15min
            2 - 1day
            3 - rollover
            4 - 5min"
    ::= { f3PtpSOOCStatsEntry 1 }

f3PtpSOOCStatsIntervalType OBJECT-TYPE
    SYNTAX      CmPmIntervalType
    MAX-ACCESS  read-only
    STATUS      current
    DESCRIPTION
            "Indicates the type of collection, i.e. whether it is
             15 Min, 1 Day or rollover."
    ::= { f3PtpSOOCStatsEntry 2 }

f3PtpSOOCStatsValid OBJECT-TYPE
    SYNTAX      TruthValue
    MAX-ACCESS  read-only
    STATUS      current
    DESCRIPTION
            "Indicates the validity of the bin."
    ::= { f3PtpSOOCStatsEntry 3 }

f3PtpSOOCStatsAction OBJECT-TYPE
    SYNTAX      CmPmBinAction
    MAX-ACCESS  read-write
    STATUS      current
    DESCRIPTION
            "Allows the Manager to clear the bin."
    ::= { f3PtpSOOCStatsEntry 4 }

f3PtpSOOCStatsMinOffsetFromMaster OBJECT-TYPE
     SYNTAX     ScaledNanoseconds  
     MAX-ACCESS read-only
     STATUS     current
     DESCRIPTION
         "Minimum Offset from Master"
     ::= { f3PtpSOOCStatsEntry 5 }

f3PtpSOOCStatsMaxOffsetFromMaster OBJECT-TYPE
     SYNTAX     ScaledNanoseconds  
     MAX-ACCESS read-only
     STATUS     current
     DESCRIPTION
         "Maximum Offset from Master"
     ::= { f3PtpSOOCStatsEntry 6 }

f3PtpSOOCStatsAvgOffsetFromMaster OBJECT-TYPE
     SYNTAX     ScaledNanoseconds  
     MAX-ACCESS read-only
     STATUS     current
     DESCRIPTION
         "Average Offset from Master"
     ::= { f3PtpSOOCStatsEntry 7 }

f3PtpSOOCStatsMinMeanPathDelay OBJECT-TYPE
     SYNTAX     ScaledNanoseconds 
     MAX-ACCESS read-only
     STATUS     current
     DESCRIPTION
         "The minimum mean path delay at the SOOC."
     ::= { f3PtpSOOCStatsEntry 8 }

f3PtpSOOCStatsMaxMeanPathDelay OBJECT-TYPE
     SYNTAX     ScaledNanoseconds 
     MAX-ACCESS read-only
     STATUS     current
     DESCRIPTION
         "The maximum mean path delay at the SOOC."
     ::= { f3PtpSOOCStatsEntry 9 }

f3PtpSOOCStatsAvgMeanPathDelay OBJECT-TYPE
     SYNTAX     ScaledNanoseconds 
     MAX-ACCESS read-only
     STATUS     current
     DESCRIPTION
         "The average mean path delay at the SOOC."
     ::= { f3PtpSOOCStatsEntry 10 }

f3PtpSOOCStatsMinSyncPathDelay OBJECT-TYPE
     SYNTAX     ScaledNanoseconds 
     MAX-ACCESS read-only
     STATUS     current
     DESCRIPTION
         "The minimum mean path delay of Sync messages at the SOOC."
     ::= { f3PtpSOOCStatsEntry 11 }

f3PtpSOOCStatsMaxSyncPathDelay OBJECT-TYPE
     SYNTAX     ScaledNanoseconds 
     MAX-ACCESS read-only
     STATUS     current
     DESCRIPTION
         "The maximum mean path delay of Sync messages at the SOOC."
     ::= { f3PtpSOOCStatsEntry 12 }

f3PtpSOOCStatsAvgSyncPathDelay OBJECT-TYPE
     SYNTAX     ScaledNanoseconds
     MAX-ACCESS read-only
     STATUS     current
     DESCRIPTION
         "The average mean path delay of Sync messages at the SOOC."
     ::= { f3PtpSOOCStatsEntry 13 }

f3PtpSOOCStatsMinSyncPDV OBJECT-TYPE
     SYNTAX     ScaledNanoseconds
     MAX-ACCESS read-only
     STATUS     current
     DESCRIPTION
         "The minimum Sync message path delay variation at the SOOC."
     ::= { f3PtpSOOCStatsEntry 14 }

f3PtpSOOCStatsMaxSyncPDV OBJECT-TYPE
     SYNTAX     ScaledNanoseconds
     MAX-ACCESS read-only
     STATUS     current
     DESCRIPTION
         "The maximum Sync message path delay variation at the SOOC."
     ::= { f3PtpSOOCStatsEntry 15 }

f3PtpSOOCStatsAvgSyncPDV OBJECT-TYPE
     SYNTAX     ScaledNanoseconds
     MAX-ACCESS read-only
     STATUS     current
     DESCRIPTION
         "The average Sync message packet delay variation at the SOOC."
     ::= { f3PtpSOOCStatsEntry 16 }

f3PtpSOOCStatsMgmtMsgsDiscarded OBJECT-TYPE
     SYNTAX     PerfCounter64
     MAX-ACCESS read-only
     STATUS     current
     DESCRIPTION
         "The number of PTP management messages discarded at the SOOC."
     ::= { f3PtpSOOCStatsEntry 17 }

f3PtpSOOCStatsInvalidMsgLenDiscards OBJECT-TYPE
     SYNTAX     PerfCounter64
     MAX-ACCESS read-only
     STATUS     current
     DESCRIPTION
         "The number of messages discarded due to invalid message length at the SOOC."
     ::= { f3PtpSOOCStatsEntry 18 }

f3PtpSOOCStatsUnknownMasterDiscards OBJECT-TYPE
     SYNTAX     PerfCounter64
     MAX-ACCESS read-only
     STATUS     current
     DESCRIPTION
         "The number of messages discard due to unknown Master at the SOOC."
     ::= { f3PtpSOOCStatsEntry 19 }

f3PtpSOOCStatsUnknownDomainDiscards OBJECT-TYPE
     SYNTAX     PerfCounter64
     MAX-ACCESS read-only
     STATUS     current
     DESCRIPTION
         "The number of messages discard due to unknown domain at the SOOC."
     ::= { f3PtpSOOCStatsEntry 20 }

f3PtpSOOCStatsMulticastAnnounceDiscards OBJECT-TYPE
     SYNTAX     PerfCounter64
     MAX-ACCESS read-only
     STATUS     current
     DESCRIPTION
         "The number of multicast Announce message discards at the SOOC."
     ::= { f3PtpSOOCStatsEntry 21 }

f3PtpSOOCStatsOutOfSeqAnnounceMsgs OBJECT-TYPE
     SYNTAX     PerfCounter64
     MAX-ACCESS read-only
     STATUS     current
     DESCRIPTION
         "The number of out-of-sequence Announce message discards at the SOOC."
     ::= { f3PtpSOOCStatsEntry 22 }

f3PtpSOOCStatsMulticastSyncDiscards OBJECT-TYPE
     SYNTAX     PerfCounter64
     MAX-ACCESS read-only
     STATUS     current
     DESCRIPTION
         "The number of Multicast Sync discards at the SOOC."
     ::= { f3PtpSOOCStatsEntry 23 }

f3PtpSOOCStatsTwoStepSyncDiscards OBJECT-TYPE
     SYNTAX     PerfCounter64
     MAX-ACCESS read-only
     STATUS     current
     DESCRIPTION
         "The number of Two Step Sync discards at the SOOC."
     ::= { f3PtpSOOCStatsEntry 24 }

f3PtpSOOCStatsFollowupDiscards OBJECT-TYPE
     SYNTAX     PerfCounter64
     MAX-ACCESS read-only
     STATUS     current
     DESCRIPTION
         "The number of Follow up discards at the SOOC."
     ::= { f3PtpSOOCStatsEntry 25 }

f3PtpSOOCStatsDelayReqDiscards OBJECT-TYPE
     SYNTAX     PerfCounter64
     MAX-ACCESS read-only
     STATUS     current
     DESCRIPTION
         "The number of Delay Request discards at the SOOC."
     ::= { f3PtpSOOCStatsEntry 26 }

f3PtpSOOCStatsPDelayReqDiscards OBJECT-TYPE
     SYNTAX     PerfCounter64
     MAX-ACCESS read-only
     STATUS     current
     DESCRIPTION
         "The number of P-Delay Request discards at the SOOC."
     ::= { f3PtpSOOCStatsEntry 27 }

f3PtpSOOCStatsPDelayRspDiscards OBJECT-TYPE
     SYNTAX     PerfCounter64
     MAX-ACCESS read-only
     STATUS     current
     DESCRIPTION
         "The number of P-Delay Response discards at the SOOC."
     ::= { f3PtpSOOCStatsEntry 28 }

f3PtpSOOCStatsPDelayFollowupDiscards OBJECT-TYPE
     SYNTAX     PerfCounter64
     MAX-ACCESS read-only
     STATUS     current
     DESCRIPTION
         "The number of P-Delay Followup discards at the SOOC."
     ::= { f3PtpSOOCStatsEntry 29 }

f3PtpSOOCStatsInvalidTLVLenDiscards OBJECT-TYPE
     SYNTAX     PerfCounter64
     MAX-ACCESS read-only
     STATUS     current
     DESCRIPTION
         "The number of discards due to invalid TLV Length at the SOOC."
     ::= { f3PtpSOOCStatsEntry 30 }

f3PtpSOOCStatsInvalidTLVTypeDiscards OBJECT-TYPE
     SYNTAX     PerfCounter64
     MAX-ACCESS read-only
     STATUS     current
     DESCRIPTION
         "The number of discards due to invalid TLV type at the SOOC."
     ::= { f3PtpSOOCStatsEntry 31 }

f3PtpSOOCStatsMaxFwdFlowWeight OBJECT-TYPE
     SYNTAX     Integer32
     MAX-ACCESS read-write
     STATUS     current
     DESCRIPTION
         "The max forward flow weight for this entry."
     ::= { f3PtpSOOCStatsEntry 32 }

f3PtpSOOCStatsAvgFwdFlowWeight OBJECT-TYPE
     SYNTAX     Integer32
     MAX-ACCESS read-write
     STATUS     current
     DESCRIPTION
         "The average forward flow weight for this entry."
     ::= { f3PtpSOOCStatsEntry 33 }

f3PtpSOOCStatsMinRevFlowWeight OBJECT-TYPE
     SYNTAX     Integer32
     MAX-ACCESS read-write
     STATUS     current
     DESCRIPTION
         "The min reverted flow weight for this entry."
     ::= { f3PtpSOOCStatsEntry 34 }

f3PtpSOOCStatsMaxRevFlowWeight OBJECT-TYPE
     SYNTAX     Integer32
     MAX-ACCESS read-write
     STATUS     current
     DESCRIPTION
         "The max reverted flow weight for this entry."
     ::= { f3PtpSOOCStatsEntry 35 }

f3PtpSOOCStatsAvgRevFlowWeight OBJECT-TYPE
     SYNTAX     Integer32
     MAX-ACCESS read-write
     STATUS     current
     DESCRIPTION
         "The average reverted flow weight for this entry."
     ::= { f3PtpSOOCStatsEntry 36 }

f3PtpSOOCStatsNumClockRecTransients OBJECT-TYPE
     SYNTAX     Unsigned32
     MAX-ACCESS read-write
     STATUS     current
     DESCRIPTION
         "The number of clock recovery transients for this entry."
     ::= { f3PtpSOOCStatsEntry 37 }

--
-- Slave Only Ordinary Clock History Table
--
f3PtpSOOCHistoryTable OBJECT-TYPE
    SYNTAX      SEQUENCE OF F3PtpSOOCHistoryEntry
    MAX-ACCESS  not-accessible
    STATUS      current
    DESCRIPTION
            "A collection of Slave Only Ordinary Clock related statistics.  
             These reflect the current data."
    ::= { f3PtpPerformanceObjects 8 }

f3PtpSOOCHistoryEntry OBJECT-TYPE
    SYNTAX      F3PtpSOOCHistoryEntry 
    MAX-ACCESS  not-accessible
    STATUS      current
    DESCRIPTION
            "A conceptual row in the f3PtpSOOCHistoryTable.
             Entries exist in this table for each Slave Only Ordinary Clock."
    INDEX { neIndex, f3PtpTSIndex,  
            f3PtpSOOCIndex, f3PtpSOOCStatsIndex, f3PtpSOOCHistoryIndex }
    ::= { f3PtpSOOCHistoryTable 1 }

F3PtpSOOCHistoryEntry ::= SEQUENCE {
    f3PtpSOOCHistoryIndex                     Integer32,
    f3PtpSOOCHistoryTime                      DateAndTime,
    f3PtpSOOCHistoryValid                     TruthValue,
    f3PtpSOOCHistoryAction                    CmPmBinAction,
    f3PtpSOOCHistoryMinOffsetFromMaster       ScaledNanoseconds,
    f3PtpSOOCHistoryMaxOffsetFromMaster       ScaledNanoseconds,
    f3PtpSOOCHistoryAvgOffsetFromMaster       ScaledNanoseconds,
    f3PtpSOOCHistoryMinMeanPathDelay          ScaledNanoseconds,
    f3PtpSOOCHistoryMaxMeanPathDelay          ScaledNanoseconds,
    f3PtpSOOCHistoryAvgMeanPathDelay          ScaledNanoseconds,
    f3PtpSOOCHistoryMinSyncPathDelay          ScaledNanoseconds,
    f3PtpSOOCHistoryMaxSyncPathDelay          ScaledNanoseconds,
    f3PtpSOOCHistoryAvgSyncPathDelay          ScaledNanoseconds,
    f3PtpSOOCHistoryMinSyncPDV                ScaledNanoseconds,
    f3PtpSOOCHistoryMaxSyncPDV                ScaledNanoseconds,
    f3PtpSOOCHistoryAvgSyncPDV                ScaledNanoseconds,
    f3PtpSOOCHistoryMgmtMsgsDiscarded         PerfCounter64,
    f3PtpSOOCHistoryInvalidMsgLenDiscards     PerfCounter64,
    f3PtpSOOCHistoryUnknownMasterDiscards     PerfCounter64,
    f3PtpSOOCHistoryUnknownDomainDiscards     PerfCounter64,
    f3PtpSOOCHistoryMulticastAnnounceDiscards PerfCounter64,
    f3PtpSOOCHistoryOutOfSeqAnnounceMsgs      PerfCounter64,
    f3PtpSOOCHistoryMulticastSyncDiscards     PerfCounter64,
    f3PtpSOOCHistoryTwoStepSyncDiscards       PerfCounter64,
    f3PtpSOOCHistoryFollowupDiscards          PerfCounter64,
    f3PtpSOOCHistoryDelayReqDiscards          PerfCounter64,
    f3PtpSOOCHistoryPDelayReqDiscards         PerfCounter64,
    f3PtpSOOCHistoryPDelayRspDiscards         PerfCounter64,
    f3PtpSOOCHistoryPDelayFollowupDiscards    PerfCounter64,
    f3PtpSOOCHistoryInvalidTLVLenDiscards     PerfCounter64,
    f3PtpSOOCHistoryInvalidTLVTypeDiscards    PerfCounter64,
    f3PtpSOOCHistoryMaxFwdFlowWeight          Integer32,
    f3PtpSOOCHistoryAvgFwdFlowWeight          Integer32,
    f3PtpSOOCHistoryMinRevFlowWeight          Integer32,
    f3PtpSOOCHistoryMaxRevFlowWeight          Integer32,
    f3PtpSOOCHistoryAvgRevFlowWeight          Integer32,
    f3PtpSOOCHistoryNumClockRecTransients     Unsigned32
}

f3PtpSOOCHistoryIndex OBJECT-TYPE
    SYNTAX      Integer32 (1..32)
    MAX-ACCESS  not-accessible
    STATUS      current
    DESCRIPTION
            "An arbitrary integer index value used to uniquely identify
            this Slave Only Ordinary Clock statistics entry. 
            Index 1 corresponds to 15minute, index 2 to 1 day and index
            3 corresponds to rollover."
    ::= { f3PtpSOOCHistoryEntry 1 }

f3PtpSOOCHistoryTime OBJECT-TYPE
    SYNTAX      DateAndTime
    MAX-ACCESS  read-only
    STATUS      current
    DESCRIPTION
            "Indicates the time of history bin creation." 
    ::= { f3PtpSOOCHistoryEntry 2 }

f3PtpSOOCHistoryValid OBJECT-TYPE
    SYNTAX      TruthValue
    MAX-ACCESS  read-only
    STATUS      current
    DESCRIPTION
            "Indicates the validity of the bin."
    ::= { f3PtpSOOCHistoryEntry 3 }

f3PtpSOOCHistoryAction OBJECT-TYPE
    SYNTAX      CmPmBinAction
    MAX-ACCESS  read-write
    STATUS      current
    DESCRIPTION
            "Allows the Manager to clear the bin."
    ::= { f3PtpSOOCHistoryEntry 4 }

f3PtpSOOCHistoryMinOffsetFromMaster OBJECT-TYPE
     SYNTAX    ScaledNanoseconds 
     MAX-ACCESS read-only
     STATUS     current
     DESCRIPTION
         "Minimum Offset from Master"
     ::= { f3PtpSOOCHistoryEntry 5 }

f3PtpSOOCHistoryMaxOffsetFromMaster OBJECT-TYPE
     SYNTAX    ScaledNanoseconds 
     MAX-ACCESS read-only
     STATUS     current
     DESCRIPTION
         "Maximum Offset from Master"
     ::= { f3PtpSOOCHistoryEntry 6 }

f3PtpSOOCHistoryAvgOffsetFromMaster OBJECT-TYPE
     SYNTAX    ScaledNanoseconds 
     MAX-ACCESS read-only
     STATUS     current
     DESCRIPTION
         "Average Offset from Master"
     ::= { f3PtpSOOCHistoryEntry 7 }

f3PtpSOOCHistoryMinMeanPathDelay OBJECT-TYPE
     SYNTAX    ScaledNanoseconds 
     MAX-ACCESS read-only
     STATUS     current
     DESCRIPTION
         "The minimum mean path delay at the SOOC."
     ::= { f3PtpSOOCHistoryEntry 8 }

f3PtpSOOCHistoryMaxMeanPathDelay OBJECT-TYPE
     SYNTAX    ScaledNanoseconds 
     MAX-ACCESS read-only
     STATUS     current
     DESCRIPTION
         "The maximum mean path delay at the SOOC."
     ::= { f3PtpSOOCHistoryEntry 9 }

f3PtpSOOCHistoryAvgMeanPathDelay OBJECT-TYPE
     SYNTAX    ScaledNanoseconds 
     MAX-ACCESS read-only
     STATUS     current
     DESCRIPTION
         "The average mean path delay at the SOOC."
     ::= { f3PtpSOOCHistoryEntry 10 }

f3PtpSOOCHistoryMinSyncPathDelay OBJECT-TYPE
     SYNTAX    ScaledNanoseconds 
     MAX-ACCESS read-only
     STATUS     current
     DESCRIPTION
         "The minimum mean path delay of Sync messages at the SOOC."
     ::= { f3PtpSOOCHistoryEntry 11 }

f3PtpSOOCHistoryMaxSyncPathDelay OBJECT-TYPE
     SYNTAX    ScaledNanoseconds 
     MAX-ACCESS read-only
     STATUS     current
     DESCRIPTION
         "The maximum mean path delay of Sync messages at the SOOC."
     ::= { f3PtpSOOCHistoryEntry 12 }

f3PtpSOOCHistoryAvgSyncPathDelay OBJECT-TYPE
     SYNTAX    ScaledNanoseconds 
     MAX-ACCESS read-only
     STATUS     current
     DESCRIPTION
         "The average mean path delay of Sync messages at the SOOC."
     ::= { f3PtpSOOCHistoryEntry 13 }

f3PtpSOOCHistoryMinSyncPDV OBJECT-TYPE
     SYNTAX    ScaledNanoseconds 
     MAX-ACCESS read-only
     STATUS     current
     DESCRIPTION
         "The minimum Sync message path delay variation at the SOOC."
     ::= { f3PtpSOOCHistoryEntry 14 }

f3PtpSOOCHistoryMaxSyncPDV OBJECT-TYPE
     SYNTAX    ScaledNanoseconds 
     MAX-ACCESS read-only
     STATUS     current
     DESCRIPTION
         "The maximum Sync message path delay variation at the SOOC."
     ::= { f3PtpSOOCHistoryEntry 15 }

f3PtpSOOCHistoryAvgSyncPDV OBJECT-TYPE
     SYNTAX    ScaledNanoseconds 
     MAX-ACCESS read-only
     STATUS     current
     DESCRIPTION
         "The average Sync message packet delay variation at the SOOC."
     ::= { f3PtpSOOCHistoryEntry 16 }

f3PtpSOOCHistoryMgmtMsgsDiscarded OBJECT-TYPE
     SYNTAX     PerfCounter64
     MAX-ACCESS read-only
     STATUS     current
     DESCRIPTION
         "The number of PTP management messages discarded at the SOOC."
     ::= { f3PtpSOOCHistoryEntry 17 }

f3PtpSOOCHistoryInvalidMsgLenDiscards OBJECT-TYPE
     SYNTAX     PerfCounter64
     MAX-ACCESS read-only
     STATUS     current
     DESCRIPTION
         "The number of messages discarded due to invalid message length at the SOOC."
     ::= { f3PtpSOOCHistoryEntry 18 }

f3PtpSOOCHistoryUnknownMasterDiscards OBJECT-TYPE
     SYNTAX     PerfCounter64
     MAX-ACCESS read-only
     STATUS     current
     DESCRIPTION
         "The number of messages discard due to unknown Master at the SOOC."
     ::= { f3PtpSOOCHistoryEntry 19 }

f3PtpSOOCHistoryUnknownDomainDiscards OBJECT-TYPE
     SYNTAX     PerfCounter64
     MAX-ACCESS read-only
     STATUS     current
     DESCRIPTION
         "The number of messages discard due to unknown domain at the SOOC."
     ::= { f3PtpSOOCHistoryEntry 20 }

f3PtpSOOCHistoryMulticastAnnounceDiscards OBJECT-TYPE
     SYNTAX     PerfCounter64
     MAX-ACCESS read-only
     STATUS     current
     DESCRIPTION
         "The number of multicast Announce message discards at the SOOC."
     ::= { f3PtpSOOCHistoryEntry 21 }

f3PtpSOOCHistoryOutOfSeqAnnounceMsgs OBJECT-TYPE
     SYNTAX     PerfCounter64
     MAX-ACCESS read-only
     STATUS     current
     DESCRIPTION
         "The number of out-of-sequence Announce message discards at the SOOC."
     ::= { f3PtpSOOCHistoryEntry 22 }

f3PtpSOOCHistoryMulticastSyncDiscards OBJECT-TYPE
     SYNTAX     PerfCounter64
     MAX-ACCESS read-only
     STATUS     current
     DESCRIPTION
         "The number of Multicast Sync discards at the SOOC."
     ::= { f3PtpSOOCHistoryEntry 23 }

f3PtpSOOCHistoryTwoStepSyncDiscards OBJECT-TYPE
     SYNTAX     PerfCounter64
     MAX-ACCESS read-only
     STATUS     current
     DESCRIPTION
         "The number of Two Step Sync discards at the SOOC."
     ::= { f3PtpSOOCHistoryEntry 24 }

f3PtpSOOCHistoryFollowupDiscards OBJECT-TYPE
     SYNTAX     PerfCounter64
     MAX-ACCESS read-only
     STATUS     current
     DESCRIPTION
         "The number of Follow up discards at the SOOC."
     ::= { f3PtpSOOCHistoryEntry 25 }

f3PtpSOOCHistoryDelayReqDiscards OBJECT-TYPE
     SYNTAX     PerfCounter64
     MAX-ACCESS read-only
     STATUS     current
     DESCRIPTION
         "The number of Delay Request discards at the SOOC."
     ::= { f3PtpSOOCHistoryEntry 26 }

f3PtpSOOCHistoryPDelayReqDiscards OBJECT-TYPE
     SYNTAX     PerfCounter64
     MAX-ACCESS read-only
     STATUS     current
     DESCRIPTION
         "The number of P-Delay Request discards at the SOOC."
     ::= { f3PtpSOOCHistoryEntry 27 }

f3PtpSOOCHistoryPDelayRspDiscards OBJECT-TYPE
     SYNTAX     PerfCounter64
     MAX-ACCESS read-only
     STATUS     current
     DESCRIPTION
         "The number of P-Delay Response discards at the SOOC."
     ::= { f3PtpSOOCHistoryEntry 28 }

f3PtpSOOCHistoryPDelayFollowupDiscards OBJECT-TYPE
     SYNTAX     PerfCounter64
     MAX-ACCESS read-only
     STATUS     current
     DESCRIPTION
         "The number of P-Delay Followup discards at the SOOC."
     ::= { f3PtpSOOCHistoryEntry 29 }

f3PtpSOOCHistoryInvalidTLVLenDiscards OBJECT-TYPE
     SYNTAX     PerfCounter64
     MAX-ACCESS read-only
     STATUS     current
     DESCRIPTION
         "The number of discards due to invalid TLV Length at the SOOC."
     ::= { f3PtpSOOCHistoryEntry 30 }

f3PtpSOOCHistoryInvalidTLVTypeDiscards OBJECT-TYPE
     SYNTAX     PerfCounter64
     MAX-ACCESS read-only
     STATUS     current
     DESCRIPTION
         "The number of discards due to invalid TLV type at the SOOC."
     ::= { f3PtpSOOCHistoryEntry 31 }

f3PtpSOOCHistoryMaxFwdFlowWeight OBJECT-TYPE
     SYNTAX     Integer32
     MAX-ACCESS read-write
     STATUS     current
     DESCRIPTION
         "The max forward flow weight for this entry."
     ::= { f3PtpSOOCHistoryEntry 32 }

f3PtpSOOCHistoryAvgFwdFlowWeight OBJECT-TYPE
     SYNTAX     Integer32
     MAX-ACCESS read-write
     STATUS     current
     DESCRIPTION
         "The average forward flow weight for this entry."
     ::= { f3PtpSOOCHistoryEntry 33 }

f3PtpSOOCHistoryMinRevFlowWeight OBJECT-TYPE
     SYNTAX     Integer32
     MAX-ACCESS read-write
     STATUS     current
     DESCRIPTION
         "The min reverted flow weight for this entry."
     ::= { f3PtpSOOCHistoryEntry 34 }

f3PtpSOOCHistoryMaxRevFlowWeight OBJECT-TYPE
     SYNTAX     Integer32
     MAX-ACCESS read-write
     STATUS     current
     DESCRIPTION
         "The max reverted flow weight for this entry."
     ::= { f3PtpSOOCHistoryEntry 35 }

f3PtpSOOCHistoryAvgRevFlowWeight OBJECT-TYPE
     SYNTAX     Integer32
     MAX-ACCESS read-write
     STATUS     current
     DESCRIPTION
         "The average reverted flow weight for this entry."
     ::= { f3PtpSOOCHistoryEntry 36 }

f3PtpSOOCHistoryNumClockRecTransients OBJECT-TYPE
     SYNTAX     Unsigned32
     MAX-ACCESS read-write
     STATUS     current
     DESCRIPTION
         "The number of clock recovery transients for this entry."
     ::= { f3PtpSOOCHistoryEntry 37 }

--
-- Slave Only Ordinary Clock Threshold Table
--
f3PtpSOOCThresholdTable OBJECT-TYPE
    SYNTAX      SEQUENCE OF F3PtpSOOCThresholdEntry
    MAX-ACCESS  not-accessible
    STATUS      current
    DESCRIPTION
            "A table of entries that allow manageability 
             of Slave Only Ordinary Clock Thresholds. 
             Below MonTypes should be treated as nanoseconds 
             despite being ScaledNanoseconds in Stats and History:
             - f3PtpSOOCStatsMinOffsetFromMaster,
             - f3PtpSOOCStatsMaxOffsetFromMaster,
             - f3PtpSOOCStatsAvgOffsetFromMaster,
             - f3PtpSOOCStatsMinMeanPathDelay,
             - f3PtpSOOCStatsMaxMeanPathDelay,
             - f3PtpSOOCStatsAvgMeanPathDelay,
             - f3PtpSOOCStatsMinSyncPathDelay,
             - f3PtpSOOCStatsMaxSyncPathDelay,
             - f3PtpSOOCStatsAvgSyncPathDelay,
             - f3PtpSOOCStatsMinSyncPDV,
             - f3PtpSOOCStatsMaxSyncPDV,
             - f3PtpSOOCStatsAvgSyncPDV"
    ::= { f3PtpPerformanceObjects 9 }

f3PtpSOOCThresholdEntry OBJECT-TYPE
    SYNTAX      F3PtpSOOCThresholdEntry
    MAX-ACCESS  not-accessible
    STATUS      current
    DESCRIPTION
            "A conceptual row in the f3PtpSOOCThresholdTable."
    INDEX { neIndex, f3PtpTSIndex,  
            f3PtpSOOCIndex, f3PtpSOOCStatsIndex, f3PtpSOOCThresholdIndex }
    ::= { f3PtpSOOCThresholdTable 1 }

F3PtpSOOCThresholdEntry ::= SEQUENCE {
    f3PtpSOOCThresholdIndex       Integer32,
    f3PtpSOOCThresholdInterval    CmPmIntervalType,
    f3PtpSOOCThresholdVariable    VariablePointer,
    f3PtpSOOCThresholdValueLo     Unsigned32,
    f3PtpSOOCThresholdValueHi     Unsigned32,
    f3PtpSOOCThresholdMonValue    PerfCounter64
}

f3PtpSOOCThresholdIndex OBJECT-TYPE
    SYNTAX     Integer32 (1..65535)
    MAX-ACCESS not-accessible
    STATUS     current
    DESCRIPTION
        "An index that uniquely identifies an entry in the
        f3PtpSOOCThresholdTable."
    ::= { f3PtpSOOCThresholdEntry 1 }

f3PtpSOOCThresholdInterval OBJECT-TYPE
    SYNTAX     CmPmIntervalType
    MAX-ACCESS read-only
    STATUS     current
    DESCRIPTION
        "The interval over which monitored value is
        sampled and compared with the specified threshold."
    ::= { f3PtpSOOCThresholdEntry 2 }

f3PtpSOOCThresholdVariable OBJECT-TYPE
    SYNTAX     VariablePointer
    MAX-ACCESS read-only
    STATUS     current
    DESCRIPTION
        "The object identifier of the particular variable to be
        sampled."
    ::= { f3PtpSOOCThresholdEntry 3 }

f3PtpSOOCThresholdValueLo OBJECT-TYPE
    SYNTAX     Unsigned32
    MAX-ACCESS read-write
    STATUS     current
    DESCRIPTION
        "Lower 32 bits of the threshold value."
    ::= { f3PtpSOOCThresholdEntry 4 }

f3PtpSOOCThresholdValueHi OBJECT-TYPE
    SYNTAX     Unsigned32
    MAX-ACCESS read-write
    STATUS     current
    DESCRIPTION
        "Higher 32 bits of the threshold value."
    ::= { f3PtpSOOCThresholdEntry 5 }

f3PtpSOOCThresholdMonValue OBJECT-TYPE
    SYNTAX     PerfCounter64
    MAX-ACCESS read-only
    STATUS     current
    DESCRIPTION
        "Monitored value corresponding to f3PtpSOOCThresholdVariable."
    ::= { f3PtpSOOCThresholdEntry 6 }


--
-- Telecom Slave Current Statistics Table
--
f3PtpTSStatsTable OBJECT-TYPE
    SYNTAX      SEQUENCE OF F3PtpTSStatsEntry
    MAX-ACCESS  not-accessible
    STATUS      current
    DESCRIPTION
            "A collection of Telecom Slave related statistics.  
             These reflect the current data."
    ::= { f3PtpPerformanceObjects 10 }

f3PtpTSStatsEntry OBJECT-TYPE
    SYNTAX      F3PtpTSStatsEntry 
    MAX-ACCESS  not-accessible
    STATUS      current
    DESCRIPTION
            "A conceptual row in the f3PtpTSStatsTable.
             Entries exist in this table for each Telecom Slave."
    INDEX { neIndex, f3PtpTSIndex,  f3PtpTSStatsIndex }
    ::= { f3PtpTSStatsTable 1 }

F3PtpTSStatsEntry ::= SEQUENCE {
    f3PtpTSStatsIndex                Integer32,
    f3PtpTSStatsIntervalType         CmPmIntervalType,
    f3PtpTSStatsValid                TruthValue,
    f3PtpTSStatsAction               CmPmBinAction,
    f3PtpTSStatsTotalTimeCR5         Unsigned32,
    f3PtpTSStatsTotalTimeCR4         Unsigned32,
    f3PtpTSStatsTotalTimeCR3         Unsigned32,
    f3PtpTSStatsTotalTimePR5         Unsigned32,
    f3PtpTSStatsTotalTimePR4         Unsigned32,
    f3PtpTSStatsTotalTimePR3         Unsigned32
}

f3PtpTSStatsIndex OBJECT-TYPE
    SYNTAX      Integer32 (1..4)
    MAX-ACCESS  not-accessible
    STATUS      current
    DESCRIPTION
            "An arbitrary integer index value used to uniquely identify
            this Telecom Slave statistics entry. 
            1 - 15min
            2 - 1day
            3 - rollover
            4 - 5min"
    ::= { f3PtpTSStatsEntry 1 }

f3PtpTSStatsIntervalType OBJECT-TYPE
    SYNTAX      CmPmIntervalType
    MAX-ACCESS  read-only
    STATUS      current
    DESCRIPTION
            "Indicates the type of collection, i.e. whether it is
             15 Min, 1 Day or rollover."
    ::= { f3PtpTSStatsEntry 2 }

f3PtpTSStatsValid OBJECT-TYPE
    SYNTAX      TruthValue
    MAX-ACCESS  read-only
    STATUS      current
    DESCRIPTION
            "Indicates the validity of the bin."
    ::= { f3PtpTSStatsEntry 3 }

f3PtpTSStatsAction OBJECT-TYPE
    SYNTAX      CmPmBinAction
    MAX-ACCESS  read-write
    STATUS      current
    DESCRIPTION
            "Allows the Manager to clear the bin."
    ::= { f3PtpTSStatsEntry 4 }

f3PtpTSStatsTotalTimeCR5 OBJECT-TYPE
     SYNTAX     Unsigned32
     MAX-ACCESS read-only
     STATUS     current
     DESCRIPTION
         "Total Time in seconds Clock Recovery Score is 5."
     ::= { f3PtpTSStatsEntry 5 }

f3PtpTSStatsTotalTimeCR4 OBJECT-TYPE
     SYNTAX     Unsigned32
     MAX-ACCESS read-only
     STATUS     current
     DESCRIPTION
         "Total Time in seconds Clock Recovery Score is 4."
     ::= { f3PtpTSStatsEntry 6 }

f3PtpTSStatsTotalTimeCR3 OBJECT-TYPE
     SYNTAX     Unsigned32
     MAX-ACCESS read-only
     STATUS     current
     DESCRIPTION
         "Total Time in seconds Clock Recovery Score is 3."
     ::= { f3PtpTSStatsEntry 7 }

f3PtpTSStatsTotalTimePR5 OBJECT-TYPE
     SYNTAX     Unsigned32
     MAX-ACCESS read-only
     STATUS     current
     DESCRIPTION
         "Total Time in seconds Phase Recovery Score is 5."
     ::= { f3PtpTSStatsEntry 8 }

f3PtpTSStatsTotalTimePR4 OBJECT-TYPE
     SYNTAX     Unsigned32
     MAX-ACCESS read-only
     STATUS     current
     DESCRIPTION
         "Total Time in seconds Phase Recovery Score is 4."
     ::= { f3PtpTSStatsEntry 9 }

f3PtpTSStatsTotalTimePR3 OBJECT-TYPE
     SYNTAX     Unsigned32
     MAX-ACCESS read-only
     STATUS     current
     DESCRIPTION
         "Total Time in seconds Phase Recovery Score is 3."
     ::= { f3PtpTSStatsEntry 10 }

--
-- Telecom Slave History Table
--
f3PtpTSHistoryTable OBJECT-TYPE
    SYNTAX      SEQUENCE OF F3PtpTSHistoryEntry
    MAX-ACCESS  not-accessible
    STATUS      current
    DESCRIPTION
            "A collection of Telecom Slave related statistics.  
             These reflect the historical data."
    ::= { f3PtpPerformanceObjects 11 }

f3PtpTSHistoryEntry OBJECT-TYPE
    SYNTAX      F3PtpTSHistoryEntry 
    MAX-ACCESS  not-accessible
    STATUS      current
    DESCRIPTION
            "A conceptual row in the f3PtpTSHistoryTable.
             Entries exist in this table for each Telecom Slave."
    INDEX { neIndex, f3PtpTSIndex,  f3PtpTSStatsIndex, f3PtpTSHistoryIndex }
    ::= { f3PtpTSHistoryTable 1 }

F3PtpTSHistoryEntry ::= SEQUENCE {
    f3PtpTSHistoryIndex                  Integer32,
    f3PtpTSHistoryTime                   DateAndTime,
    f3PtpTSHistoryValid                  TruthValue,
    f3PtpTSHistoryAction                 CmPmBinAction,
    f3PtpTSHistoryTotalTimeCR5           Unsigned32,
    f3PtpTSHistoryTotalTimeCR4           Unsigned32,
    f3PtpTSHistoryTotalTimeCR3           Unsigned32,
    f3PtpTSHistoryTotalTimePR5           Unsigned32,
    f3PtpTSHistoryTotalTimePR4           Unsigned32,
    f3PtpTSHistoryTotalTimePR3           Unsigned32
}

f3PtpTSHistoryIndex OBJECT-TYPE
    SYNTAX      Integer32 (1..32)
    MAX-ACCESS  not-accessible
    STATUS      current
    DESCRIPTION
            "An arbitrary integer index value used to uniquely identify
            this Telecom Slave statistics entry. 
            Index 1 corresponds to 15minute, index 2 to 1 day and index
            3 corresponds to rollover."
    ::= { f3PtpTSHistoryEntry 1 }

f3PtpTSHistoryTime OBJECT-TYPE
    SYNTAX      DateAndTime 
    MAX-ACCESS  read-only
    STATUS      current
    DESCRIPTION
            "Indicates the time of history bin creation." 
    ::= { f3PtpTSHistoryEntry 2 }

f3PtpTSHistoryValid OBJECT-TYPE
    SYNTAX      TruthValue
    MAX-ACCESS  read-only
    STATUS      current
    DESCRIPTION
            "Indicates the validity of the bin."
    ::= { f3PtpTSHistoryEntry 3 }

f3PtpTSHistoryAction OBJECT-TYPE
    SYNTAX      CmPmBinAction
    MAX-ACCESS  read-write
    STATUS      current
    DESCRIPTION
            "Allows the Manager to clear the bin."
    ::= { f3PtpTSHistoryEntry 4 }

f3PtpTSHistoryTotalTimeCR5 OBJECT-TYPE
     SYNTAX     Unsigned32
     MAX-ACCESS read-only
     STATUS     current
     DESCRIPTION
         "Total Time in seconds Clock Recovery Score is 5."
     ::= { f3PtpTSHistoryEntry 5 }

f3PtpTSHistoryTotalTimeCR4 OBJECT-TYPE
     SYNTAX     Unsigned32
     MAX-ACCESS read-only
     STATUS     current
     DESCRIPTION
         "Total Time in seconds Clock Recovery Score is 4."
     ::= { f3PtpTSHistoryEntry 6 }

f3PtpTSHistoryTotalTimeCR3 OBJECT-TYPE
     SYNTAX     Unsigned32
     MAX-ACCESS read-only
     STATUS     current
     DESCRIPTION
         "Total Time in seconds Clock Recovery Score is 3."
     ::= { f3PtpTSHistoryEntry 7 }

f3PtpTSHistoryTotalTimePR5 OBJECT-TYPE
     SYNTAX     Unsigned32
     MAX-ACCESS read-only
     STATUS     current
     DESCRIPTION
         "Total Time in seconds Phase Recovery Score is 5."
     ::= { f3PtpTSHistoryEntry 8 }

f3PtpTSHistoryTotalTimePR4 OBJECT-TYPE
     SYNTAX     Unsigned32
     MAX-ACCESS read-only
     STATUS     current
     DESCRIPTION
         "Total Time in seconds Phase Recovery Score is 4."
     ::= { f3PtpTSHistoryEntry 9 }

f3PtpTSHistoryTotalTimePR3 OBJECT-TYPE
     SYNTAX     Unsigned32
     MAX-ACCESS read-only
     STATUS     current
     DESCRIPTION
         "Total Time in seconds Phase Recovery Score is 3."
     ::= { f3PtpTSHistoryEntry 10 }


--
-- Telecom Slave Threshold Table
--
f3PtpTSThresholdTable OBJECT-TYPE
    SYNTAX      SEQUENCE OF F3PtpTSThresholdEntry
    MAX-ACCESS  not-accessible
    STATUS      current
    DESCRIPTION
            "A table of entries that allow manageability of 
             Telecom Slave Thresholds."
    ::= { f3PtpPerformanceObjects 12 }

f3PtpTSThresholdEntry OBJECT-TYPE
    SYNTAX      F3PtpTSThresholdEntry
    MAX-ACCESS  not-accessible
    STATUS      current
    DESCRIPTION
            "A conceptual row in the f3PtpTSThresholdTable."
    INDEX { neIndex, f3PtpTSIndex,  
            f3PtpTSStatsIndex, f3PtpTSThresholdIndex }
    ::= { f3PtpTSThresholdTable 1 }

F3PtpTSThresholdEntry ::= SEQUENCE {
    f3PtpTSThresholdIndex       Integer32,
    f3PtpTSThresholdInterval    CmPmIntervalType,
    f3PtpTSThresholdVariable    VariablePointer,
    f3PtpTSThresholdValueLo     Unsigned32,
    f3PtpTSThresholdValueHi     Unsigned32,
    f3PtpTSThresholdMonValue    PerfCounter64
}

f3PtpTSThresholdIndex OBJECT-TYPE
    SYNTAX     Integer32 (1..65535)
    MAX-ACCESS not-accessible
    STATUS     current
    DESCRIPTION
        "An index that uniquely identifies an entry in the
        f3PtpTSThresholdTable."
    ::= { f3PtpTSThresholdEntry 1 }

f3PtpTSThresholdInterval OBJECT-TYPE
    SYNTAX     CmPmIntervalType
    MAX-ACCESS read-only
    STATUS     current
    DESCRIPTION
        "The interval over which monitored value is
        sampled and compared with the specified threshold."
    ::= { f3PtpTSThresholdEntry 2 }

f3PtpTSThresholdVariable OBJECT-TYPE
    SYNTAX     VariablePointer
    MAX-ACCESS read-only
    STATUS     current
    DESCRIPTION
        "The object identifier of the particular variable to be
        sampled."
    ::= { f3PtpTSThresholdEntry 3 }

f3PtpTSThresholdValueLo OBJECT-TYPE
    SYNTAX     Unsigned32
    MAX-ACCESS read-write
    STATUS     current
    DESCRIPTION
        "Lower 32 bits of the threshold value."
    ::= { f3PtpTSThresholdEntry 4 }

f3PtpTSThresholdValueHi OBJECT-TYPE
    SYNTAX     Unsigned32
    MAX-ACCESS read-write
    STATUS     current
    DESCRIPTION
        "Higher 32 bits of the threshold value."
    ::= { f3PtpTSThresholdEntry 5 }

f3PtpTSThresholdMonValue OBJECT-TYPE
    SYNTAX     PerfCounter64
    MAX-ACCESS read-only
    STATUS     current
    DESCRIPTION
        "Monitored value corresponding to f3PtpTSThresholdVariable."
    ::= { f3PtpTSThresholdEntry 6 }

--
-- Master Clock Interface current data
--
f3PtpMCIStatsTable OBJECT-TYPE
    SYNTAX      SEQUENCE OF F3PtpMCIStatsEntry
    MAX-ACCESS  not-accessible
    STATUS      current
    DESCRIPTION
            "A collection of Master Clock Interface related statistics.  
             These reflect the current data."
    ::= { f3PtpPerformanceObjects 13 }

f3PtpMCIStatsEntry OBJECT-TYPE
    SYNTAX      F3PtpMCIStatsEntry 
    MAX-ACCESS  not-accessible
    STATUS      current
    DESCRIPTION
            "A conceptual row in the f3PtpMCIStatsTable.
             Entries exist in this table for each Telecom Slave."
    INDEX { neIndex, f3PtpBCIndex, f3PtpMCIIndex, f3PtpMCIStatsIndex }
    ::= { f3PtpMCIStatsTable 1 }

F3PtpMCIStatsEntry ::= SEQUENCE {
    f3PtpMCIStatsIndex                    Integer32,
    f3PtpMCIStatsIntervalType             CmPmIntervalType,
    f3PtpMCIStatsValid                    TruthValue,
    f3PtpMCIStatsAction                   CmPmBinAction,
    f3PtpMCIStatsPtpDiscards              PerfCounter64,
    f3PtpMCIStatsSyncDeniedEvents         PerfCounter64,
    f3PtpMCIStatsDelayRspDeniedEvents     PerfCounter64,
    f3PtpMCIStatsAnnounceDeniedEvents     PerfCounter64,
    f3PtpMCIStatsSyncCancelledEvents      PerfCounter64,
    f3PtpMCIStatsDelayRspCancelledEvents  PerfCounter64,
    f3PtpMCIStatsAnnounceCancelledEvents  PerfCounter64,
    f3PtpMCIStatsDynamicSlavesLearnt      PerfCounter64,
    f3PtpMCIStatsDynamicSlavesDropped     PerfCounter64
}

f3PtpMCIStatsIndex OBJECT-TYPE
    SYNTAX      Integer32 (1..4)
    MAX-ACCESS  not-accessible
    STATUS      current
    DESCRIPTION
            "An arbitrary integer index value used to uniquely identify
            this Master Clock Interface statistics entry. 
            1 - 15min
            2 - 1day
            3 - rollover
            4 - 5min"
    ::= { f3PtpMCIStatsEntry 1 }

f3PtpMCIStatsIntervalType OBJECT-TYPE
    SYNTAX      CmPmIntervalType
    MAX-ACCESS  read-only
    STATUS      current
    DESCRIPTION
            "Indicates the type of collection, i.e. whether it is
             15 Min, 1 Day or rollover."
    ::= { f3PtpMCIStatsEntry 2 }

f3PtpMCIStatsValid OBJECT-TYPE
    SYNTAX      TruthValue
    MAX-ACCESS  read-only
    STATUS      current
    DESCRIPTION
            "Indicates the validity of the bin."
    ::= { f3PtpMCIStatsEntry 3 }

f3PtpMCIStatsAction OBJECT-TYPE
    SYNTAX      CmPmBinAction
    MAX-ACCESS  read-write
    STATUS      current
    DESCRIPTION
            "Allows the Manager to clear the bin."
    ::= { f3PtpMCIStatsEntry 4 }

f3PtpMCIStatsPtpDiscards OBJECT-TYPE
    SYNTAX      PerfCounter64
    MAX-ACCESS  read-only
    STATUS      current
    DESCRIPTION
            "Count of PTP messages that have been discarded by the MCI since either 
             Source IP, PTP Domain number, Port Identity did not match any 
             Remote Slave clock."
    ::= { f3PtpMCIStatsEntry 5 }

f3PtpMCIStatsSyncDeniedEvents OBJECT-TYPE
    SYNTAX      PerfCounter64
    MAX-ACCESS  read-only
    STATUS      current
    DESCRIPTION
            "Count of Sync service denied events."
    ::= { f3PtpMCIStatsEntry 6 }

f3PtpMCIStatsDelayRspDeniedEvents OBJECT-TYPE
    SYNTAX      PerfCounter64
    MAX-ACCESS  read-only
    STATUS      current
    DESCRIPTION
            "Count of Delay Response service denied events."
    ::= { f3PtpMCIStatsEntry 7 }

f3PtpMCIStatsAnnounceDeniedEvents OBJECT-TYPE
    SYNTAX      PerfCounter64
    MAX-ACCESS  read-only
    STATUS      current
    DESCRIPTION
            "Count of Announce service denied events."
    ::= { f3PtpMCIStatsEntry 8 }

f3PtpMCIStatsSyncCancelledEvents OBJECT-TYPE
    SYNTAX      PerfCounter64
    MAX-ACCESS  read-only
    STATUS      current
    DESCRIPTION
            "Count of Sync service canceled events initiated by the Remote Slave Clocks."
    ::= { f3PtpMCIStatsEntry 9 }

f3PtpMCIStatsDelayRspCancelledEvents OBJECT-TYPE
    SYNTAX      PerfCounter64
    MAX-ACCESS  read-only
    STATUS      current
    DESCRIPTION
            "Count of Delay Response service canceled events initiated by the 
             Remote Slave Clocks."
    ::= { f3PtpMCIStatsEntry 10 }

f3PtpMCIStatsAnnounceCancelledEvents OBJECT-TYPE
    SYNTAX      PerfCounter64
    MAX-ACCESS  read-only
    STATUS      current
    DESCRIPTION
            "Count of Announce service canceled events initiated by the 
             Remote Slave Clocks."
    ::= { f3PtpMCIStatsEntry 11 }

f3PtpMCIStatsDynamicSlavesLearnt OBJECT-TYPE
    SYNTAX      PerfCounter64
    MAX-ACCESS  read-only
    STATUS      current
    DESCRIPTION
            "Count of Successfully learned Dynamic Slaves."
    ::= { f3PtpMCIStatsEntry 12 }

f3PtpMCIStatsDynamicSlavesDropped OBJECT-TYPE
    SYNTAX      PerfCounter64
    MAX-ACCESS  read-only
    STATUS      current
    DESCRIPTION
            "Count of Dynamic Slaves removed from the Remote Slaves table due to 
             lease expired."
    ::= { f3PtpMCIStatsEntry 13 }

--
-- Master Clock Interface history data
--
f3PtpMCIHistoryTable OBJECT-TYPE
    SYNTAX      SEQUENCE OF F3PtpMCIHistoryEntry
    MAX-ACCESS  not-accessible
    STATUS      current
    DESCRIPTION
            "A collection of Master Clock Interface related history data.  
             These reflect the current data."
    ::= { f3PtpPerformanceObjects 14 }

f3PtpMCIHistoryEntry OBJECT-TYPE
    SYNTAX      F3PtpMCIHistoryEntry 
    MAX-ACCESS  not-accessible
    STATUS      current
    DESCRIPTION
            "A conceptual row in the f3PtpMCIHistoryTable.
             Entries exist in this table for each Master Clock Interface."
    INDEX { neIndex, f3PtpBCIndex, f3PtpMCIIndex, f3PtpMCIStatsIndex,
            f3PtpMCIHistoryIndex }
    ::= { f3PtpMCIHistoryTable 1 }

F3PtpMCIHistoryEntry ::= SEQUENCE {
    f3PtpMCIHistoryIndex                    Integer32,
    f3PtpMCIHistoryTime                     DateAndTime,
    f3PtpMCIHistoryValid                    TruthValue,
    f3PtpMCIHistoryAction                   CmPmBinAction,
    f3PtpMCIHistoryPtpDiscards              PerfCounter64,
    f3PtpMCIHistorySyncDeniedEvents         PerfCounter64,
    f3PtpMCIHistoryDelayRspDeniedEvents     PerfCounter64,
    f3PtpMCIHistoryAnnounceDeniedEvents     PerfCounter64,
    f3PtpMCIHistorySyncCancelledEvents      PerfCounter64,
    f3PtpMCIHistoryDelayRspCancelledEvents  PerfCounter64,
    f3PtpMCIHistoryAnnounceCancelledEvents  PerfCounter64,
    f3PtpMCIHistoryDynamicSlavesLearnt      PerfCounter64,
    f3PtpMCIHistoryDynamicSlavesDropped     PerfCounter64
}

f3PtpMCIHistoryIndex OBJECT-TYPE
    SYNTAX      Integer32 (1..32)
    MAX-ACCESS  not-accessible
    STATUS      current
    DESCRIPTION
            "An arbitrary integer index value used to uniquely identify
            this Master Clock Interface PM history entry."
    ::= { f3PtpMCIHistoryEntry 1 }

f3PtpMCIHistoryTime OBJECT-TYPE
    SYNTAX      DateAndTime 
    MAX-ACCESS  read-only
    STATUS      current
    DESCRIPTION
            "Indicates the time of history bin creation." 
    ::= { f3PtpMCIHistoryEntry 2 }

f3PtpMCIHistoryValid OBJECT-TYPE
    SYNTAX      TruthValue
    MAX-ACCESS  read-only
    STATUS      current
    DESCRIPTION
            "Indicates the validity of the bin."
    ::= { f3PtpMCIHistoryEntry 3 }

f3PtpMCIHistoryAction OBJECT-TYPE
    SYNTAX      CmPmBinAction
    MAX-ACCESS  read-write
    STATUS      current
    DESCRIPTION
            "Allows the Manager to clear the bin."
    ::= { f3PtpMCIHistoryEntry 4 }

f3PtpMCIHistoryPtpDiscards OBJECT-TYPE
    SYNTAX      PerfCounter64
    MAX-ACCESS  read-only
    STATUS      current
    DESCRIPTION
            "Count of PTP messages that have been discarded by the MCI since either 
             Source IP, PTP Domain number, Port Identity did not match any 
             Remote Slave clock."
    ::= { f3PtpMCIHistoryEntry 5 }

f3PtpMCIHistorySyncDeniedEvents OBJECT-TYPE
    SYNTAX      PerfCounter64
    MAX-ACCESS  read-only
    STATUS      current
    DESCRIPTION
            "Count of Sync service denied events."
    ::= { f3PtpMCIHistoryEntry 6 }

f3PtpMCIHistoryDelayRspDeniedEvents OBJECT-TYPE
    SYNTAX      PerfCounter64
    MAX-ACCESS  read-only
    STATUS      current
    DESCRIPTION
            "Count of Delay Response service denied events."
    ::= { f3PtpMCIHistoryEntry 7 }

f3PtpMCIHistoryAnnounceDeniedEvents OBJECT-TYPE
    SYNTAX      PerfCounter64
    MAX-ACCESS  read-only
    STATUS      current
    DESCRIPTION
            "Count of Announce service denied events."
    ::= { f3PtpMCIHistoryEntry 8 }

f3PtpMCIHistorySyncCancelledEvents OBJECT-TYPE
    SYNTAX      PerfCounter64
    MAX-ACCESS  read-only
    STATUS      current
    DESCRIPTION
            "Count of Sync service canceled events initiated by the Remote Slave Clocks."
    ::= { f3PtpMCIHistoryEntry 9 }

f3PtpMCIHistoryDelayRspCancelledEvents OBJECT-TYPE
    SYNTAX      PerfCounter64
    MAX-ACCESS  read-only
    STATUS      current
    DESCRIPTION
            "Count of Delay Response service canceled events initiated by the 
             Remote Slave Clocks."
    ::= { f3PtpMCIHistoryEntry 10 }

f3PtpMCIHistoryAnnounceCancelledEvents OBJECT-TYPE
    SYNTAX      PerfCounter64
    MAX-ACCESS  read-only
    STATUS      current
    DESCRIPTION
            "Count of Announce service canceled events initiated by the 
             Remote Slave Clocks."
    ::= { f3PtpMCIHistoryEntry 11 }

f3PtpMCIHistoryDynamicSlavesLearnt OBJECT-TYPE
    SYNTAX      PerfCounter64
    MAX-ACCESS  read-only
    STATUS      current
    DESCRIPTION
            "Count of Successfully learned Dynamic Slaves."
    ::= { f3PtpMCIHistoryEntry 12 }

f3PtpMCIHistoryDynamicSlavesDropped OBJECT-TYPE
    SYNTAX      PerfCounter64
    MAX-ACCESS  read-only
    STATUS      current
    DESCRIPTION
            "Count of Dynamic Slaves removed from the Remote Slaves table due to 
             lease expired."
    ::= { f3PtpMCIHistoryEntry 13 }

--
-- Master Clock Interface Threshold Table
--
f3PtpMCIThresholdTable OBJECT-TYPE
    SYNTAX      SEQUENCE OF F3PtpMCIThresholdEntry
    MAX-ACCESS  not-accessible
    STATUS      current
    DESCRIPTION
            "A table of entries that allow manageability of 
             Master Clock Interface Thresholds."
    ::= { f3PtpPerformanceObjects 15 }

f3PtpMCIThresholdEntry OBJECT-TYPE
    SYNTAX      F3PtpMCIThresholdEntry
    MAX-ACCESS  not-accessible
    STATUS      current
    DESCRIPTION
            "A conceptual row in the f3PtpMCIThresholdTable."
    INDEX { neIndex, f3PtpBCIndex, f3PtpMCIIndex, f3PtpMCIStatsIndex, 
            f3PtpMCIThresholdIndex }
    ::= { f3PtpMCIThresholdTable 1 }

F3PtpMCIThresholdEntry ::= SEQUENCE {
    f3PtpMCIThresholdIndex       Integer32,
    f3PtpMCIThresholdInterval    CmPmIntervalType,
    f3PtpMCIThresholdVariable    VariablePointer,
    f3PtpMCIThresholdValueLo     Unsigned32,
    f3PtpMCIThresholdValueHi     Unsigned32,
    f3PtpMCIThresholdMonValue    PerfCounter64
}

f3PtpMCIThresholdIndex OBJECT-TYPE
    SYNTAX     Integer32 (1..65535)
    MAX-ACCESS not-accessible
    STATUS     current
    DESCRIPTION
        "An index that uniquely identifies an entry in the
        f3PtpMCIThresholdTable."
    ::= { f3PtpMCIThresholdEntry 1 }

f3PtpMCIThresholdInterval OBJECT-TYPE
    SYNTAX     CmPmIntervalType
    MAX-ACCESS read-only
    STATUS     current
    DESCRIPTION
        "The interval over which monitored value is
        sampled and compared with the specified threshold."
    ::= { f3PtpMCIThresholdEntry 2 }

f3PtpMCIThresholdVariable OBJECT-TYPE
    SYNTAX     VariablePointer
    MAX-ACCESS read-only
    STATUS     current
    DESCRIPTION
        "The object identifier of the particular variable to be
        sampled."
    ::= { f3PtpMCIThresholdEntry 3 }

f3PtpMCIThresholdValueLo OBJECT-TYPE
    SYNTAX     Unsigned32
    MAX-ACCESS read-write
    STATUS     current
    DESCRIPTION
        "Lower 32 bits of the threshold value."
    ::= { f3PtpMCIThresholdEntry 4 }

f3PtpMCIThresholdValueHi OBJECT-TYPE
    SYNTAX     Unsigned32
    MAX-ACCESS read-write
    STATUS     current
    DESCRIPTION
        "Higher 32 bits of the threshold value."
    ::= { f3PtpMCIThresholdEntry 5 }

f3PtpMCIThresholdMonValue OBJECT-TYPE
    SYNTAX     PerfCounter64
    MAX-ACCESS read-only
    STATUS     current
    DESCRIPTION
        "Monitored value corresponding to f3PtpMCIThresholdVariable."
    ::= { f3PtpMCIThresholdEntry 6 }

--
-- Remote Slave current data
--
f3PtpRemoteSlaveStatsTable OBJECT-TYPE
    SYNTAX      SEQUENCE OF F3PtpRemoteSlaveStatsEntry
    MAX-ACCESS  not-accessible
    STATUS      current
    DESCRIPTION
            "A collection of Remote Slave related statistics.  
             These reflect the current data."
    ::= { f3PtpPerformanceObjects 16 }

f3PtpRemoteSlaveStatsEntry OBJECT-TYPE
    SYNTAX      F3PtpRemoteSlaveStatsEntry 
    MAX-ACCESS  not-accessible
    STATUS      current
    DESCRIPTION
            "A conceptual row in the f3PtpRemoteSlaveStatsTable.
             Entries exist in this table for each Remote Slave."
    INDEX { neIndex, f3PtpBCIndex, f3PtpMCIIndex, f3PtpRemoteSlaveStatsSlaveType, f3PtpRemoteSlaveStatsSlaveIndex,
            f3PtpRemoteSlaveStatsIndex }
    ::= { f3PtpRemoteSlaveStatsTable 1 }

F3PtpRemoteSlaveStatsEntry ::= SEQUENCE {
    f3PtpRemoteSlaveStatsSlaveType                RemoteSlaveType,
    f3PtpRemoteSlaveStatsSlaveIndex               Integer32,
    f3PtpRemoteSlaveStatsIndex                    Integer32,
    f3PtpRemoteSlaveStatsIntervalType             CmPmIntervalType,
    f3PtpRemoteSlaveStatsValid                    TruthValue,
    f3PtpRemoteSlaveStatsAction                   CmPmBinAction,
    f3PtpRemoteSlaveStatsSyncMsgsGen              PerfCounter64,
    f3PtpRemoteSlaveStatsDelayRspMsgsGen          PerfCounter64,
    f3PtpRemoteSlaveStatsAnnounceMsgsGen          PerfCounter64,
    f3PtpRemoteSlaveStatsSignallingMsgsGen        PerfCounter64,
    f3PtpRemoteSlaveStatsDelayReqMsgsRx           PerfCounter64,
    f3PtpRemoteSlaveStatsSignallingMsgsRx         PerfCounter64,
    f3PtpRemoteSlaveStatsDelayReqMsgsDropped      PerfCounter64,
    f3PtpRemoteSlaveStatsInvalidTLVLenDiscards    PerfCounter64,
    f3PtpRemoteSlaveStatsInvalidTLVTypeDiscards   PerfCounter64,
    f3PtpRemoteSlaveStatsTimesSyncLeaseExp        PerfCounter64,
    f3PtpRemoteSlaveStatsTimesDelayRspLeaseExp    PerfCounter64,
    f3PtpRemoteSlaveStatsTimesAnnounceLeaseExp    PerfCounter64
}

f3PtpRemoteSlaveStatsSlaveType OBJECT-TYPE
    SYNTAX      RemoteSlaveType
    MAX-ACCESS  not-accessible
    STATUS      current
    DESCRIPTION
            "This object indicates if this row referts to Static or Dynamic Remote Slave."
    ::= { f3PtpRemoteSlaveStatsEntry 1 }

f3PtpRemoteSlaveStatsSlaveIndex OBJECT-TYPE
    SYNTAX      Integer32
    MAX-ACCESS  not-accessible
    STATUS      current
    DESCRIPTION
            "Index of a Static or Dynamic Remote Slave.
             When f3PtpRemoteSlaveStatsSlaveType is 'static' then this object referts to f3PtpStaticRemoteSlaveIndex.
             When f3PtpRemoteSlaveStatsSlaveType is 'dynamic' then this object referts to f3PtpDynamicRemoteSlaveIndex."
    ::= { f3PtpRemoteSlaveStatsEntry 2 }

f3PtpRemoteSlaveStatsIndex OBJECT-TYPE
    SYNTAX      Integer32 (1..4)
    MAX-ACCESS  not-accessible
    STATUS      current
    DESCRIPTION
            "An arbitrary integer index value used to uniquely identify
            this Remote Slave statistics entry. 
            1 - 15min
            2 - 1day
            3 - rollover
            4 - 5min"
    ::= { f3PtpRemoteSlaveStatsEntry 3 }

f3PtpRemoteSlaveStatsIntervalType OBJECT-TYPE
    SYNTAX      CmPmIntervalType
    MAX-ACCESS  read-only
    STATUS      current
    DESCRIPTION
            "Indicates the type of collection, i.e. whether it is
             15 Min, 1 Day or rollover."
    ::= { f3PtpRemoteSlaveStatsEntry 4 }

f3PtpRemoteSlaveStatsValid OBJECT-TYPE
    SYNTAX      TruthValue
    MAX-ACCESS  read-only
    STATUS      current
    DESCRIPTION
            "Indicates the validity of the bin."
    ::= { f3PtpRemoteSlaveStatsEntry 5 }

f3PtpRemoteSlaveStatsAction OBJECT-TYPE
    SYNTAX      CmPmBinAction
    MAX-ACCESS  read-write
    STATUS      current
    DESCRIPTION
            "Allows the Manager to clear the bin."
    ::= { f3PtpRemoteSlaveStatsEntry 6 }

f3PtpRemoteSlaveStatsSyncMsgsGen OBJECT-TYPE
    SYNTAX      PerfCounter64
    MAX-ACCESS  read-only
    STATUS      current
    DESCRIPTION
            "Total Sync messages generated."
    ::= { f3PtpRemoteSlaveStatsEntry 7 }

f3PtpRemoteSlaveStatsDelayRspMsgsGen OBJECT-TYPE
    SYNTAX      PerfCounter64
    MAX-ACCESS  read-only
    STATUS      current
    DESCRIPTION
            "Total Delay Response messages generated."
    ::= { f3PtpRemoteSlaveStatsEntry 8 }

f3PtpRemoteSlaveStatsAnnounceMsgsGen OBJECT-TYPE
    SYNTAX      PerfCounter64
    MAX-ACCESS  read-only
    STATUS      current
    DESCRIPTION
            "Total Announce messages generated."
    ::= { f3PtpRemoteSlaveStatsEntry 9 }

f3PtpRemoteSlaveStatsSignallingMsgsGen OBJECT-TYPE
    SYNTAX      PerfCounter64
    MAX-ACCESS  read-only
    STATUS      current
    DESCRIPTION
            "Total Signalling messages generated."
    ::= { f3PtpRemoteSlaveStatsEntry 10 }

f3PtpRemoteSlaveStatsDelayReqMsgsRx OBJECT-TYPE
    SYNTAX      PerfCounter64
    MAX-ACCESS  read-only
    STATUS      current
    DESCRIPTION
            "Total Delay Request messages received."
    ::= { f3PtpRemoteSlaveStatsEntry 11 }

f3PtpRemoteSlaveStatsSignallingMsgsRx OBJECT-TYPE
    SYNTAX      PerfCounter64
    MAX-ACCESS  read-only
    STATUS      current
    DESCRIPTION
            "Total Signalling messages received."
    ::= { f3PtpRemoteSlaveStatsEntry 12 }

f3PtpRemoteSlaveStatsDelayReqMsgsDropped OBJECT-TYPE
    SYNTAX      PerfCounter64
    MAX-ACCESS  read-only
    STATUS      current
    DESCRIPTION
            "Total Delay Request messages dropped."
    ::= { f3PtpRemoteSlaveStatsEntry 13 }

f3PtpRemoteSlaveStatsInvalidTLVLenDiscards OBJECT-TYPE
    SYNTAX      PerfCounter64
    MAX-ACCESS  read-only
    STATUS      current
    DESCRIPTION
            "Total number of PTP messages discarded due to invalid PTP TLV length."
    ::= { f3PtpRemoteSlaveStatsEntry 14 }

f3PtpRemoteSlaveStatsInvalidTLVTypeDiscards OBJECT-TYPE
    SYNTAX      PerfCounter64
    MAX-ACCESS  read-only
    STATUS      current
    DESCRIPTION
            "Total number of PTP messages discarded due to invalid PTP TLV type."
    ::= { f3PtpRemoteSlaveStatsEntry 15 }

f3PtpRemoteSlaveStatsTimesSyncLeaseExp OBJECT-TYPE
    SYNTAX      PerfCounter64
    MAX-ACCESS  read-only
    STATUS      current
    DESCRIPTION
            "Count of Sync service lease duration expired events."
    ::= { f3PtpRemoteSlaveStatsEntry 16 }

f3PtpRemoteSlaveStatsTimesDelayRspLeaseExp OBJECT-TYPE
    SYNTAX      PerfCounter64
    MAX-ACCESS  read-only
    STATUS      current
    DESCRIPTION
            "Count of Delay Response service lease duration expired events."
    ::= { f3PtpRemoteSlaveStatsEntry 17 }

f3PtpRemoteSlaveStatsTimesAnnounceLeaseExp OBJECT-TYPE
    SYNTAX      PerfCounter64
    MAX-ACCESS  read-only
    STATUS      current
    DESCRIPTION
            "Count of Announce service lease duration expired events."
    ::= { f3PtpRemoteSlaveStatsEntry 18 }

--
-- Remote Slave history data
--
f3PtpRemoteSlaveHistoryTable OBJECT-TYPE
    SYNTAX      SEQUENCE OF F3PtpRemoteSlaveHistoryEntry
    MAX-ACCESS  not-accessible
    STATUS      current
    DESCRIPTION
            "A collection of Remote Slave related history.  
             These reflect the current data."
    ::= { f3PtpPerformanceObjects 17 }

f3PtpRemoteSlaveHistoryEntry OBJECT-TYPE
    SYNTAX      F3PtpRemoteSlaveHistoryEntry 
    MAX-ACCESS  not-accessible
    STATUS      current
    DESCRIPTION
            "A conceptual row in the f3PtpRemoteSlaveHistoryTable.
             Entries exist in this table for each Remote Slave."
    INDEX { neIndex, f3PtpBCIndex, f3PtpMCIIndex, f3PtpRemoteSlaveStatsSlaveType, f3PtpRemoteSlaveStatsSlaveIndex,
            f3PtpRemoteSlaveStatsIndex, f3PtpRemoteSlaveHistoryIndex }
    ::= { f3PtpRemoteSlaveHistoryTable 1 }

F3PtpRemoteSlaveHistoryEntry ::= SEQUENCE {
    f3PtpRemoteSlaveHistoryIndex                    Integer32,
    f3PtpRemoteSlaveHistoryTime                     DateAndTime,
    f3PtpRemoteSlaveHistoryValid                    TruthValue,
    f3PtpRemoteSlaveHistoryAction                   CmPmBinAction,
    f3PtpRemoteSlaveHistorySyncMsgsGen              PerfCounter64,
    f3PtpRemoteSlaveHistoryDelayRspMsgsGen          PerfCounter64,
    f3PtpRemoteSlaveHistoryAnnounceMsgsGen          PerfCounter64,
    f3PtpRemoteSlaveHistorySignallingMsgsGen        PerfCounter64,
    f3PtpRemoteSlaveHistoryDelayReqMsgsRx           PerfCounter64,
    f3PtpRemoteSlaveHistorySignallingMsgsRx         PerfCounter64,
    f3PtpRemoteSlaveHistoryDelayReqMsgsDropped      PerfCounter64,
    f3PtpRemoteSlaveHistoryInvalidTLVLenDiscards    PerfCounter64,
    f3PtpRemoteSlaveHistoryInvalidTLVTypeDiscards   PerfCounter64,
    f3PtpRemoteSlaveHistoryTimesSyncLeaseExp        PerfCounter64,
    f3PtpRemoteSlaveHistoryTimesDelayRspLeaseExp    PerfCounter64,
    f3PtpRemoteSlaveHistoryTimesAnnounceLeaseExp    PerfCounter64
}


f3PtpRemoteSlaveHistoryIndex OBJECT-TYPE
    SYNTAX      Integer32 (1..32)
    MAX-ACCESS  not-accessible
    STATUS      current
    DESCRIPTION
            "An arbitrary integer index value used to uniquely identify
             this Remote Slave PM history entry."
    ::= { f3PtpRemoteSlaveHistoryEntry 1 }

f3PtpRemoteSlaveHistoryTime OBJECT-TYPE
    SYNTAX      DateAndTime 
    MAX-ACCESS  read-only
    STATUS      current
    DESCRIPTION
            "Indicates the time of history bin creation." 
    ::= { f3PtpRemoteSlaveHistoryEntry 2 }

f3PtpRemoteSlaveHistoryValid OBJECT-TYPE
    SYNTAX      TruthValue
    MAX-ACCESS  read-only
    STATUS      current
    DESCRIPTION
            "Indicates the validity of the bin."
    ::= { f3PtpRemoteSlaveHistoryEntry 3 }

f3PtpRemoteSlaveHistoryAction OBJECT-TYPE
    SYNTAX      CmPmBinAction
    MAX-ACCESS  read-write
    STATUS      current
    DESCRIPTION
            "Allows the Manager to clear the bin."
    ::= { f3PtpRemoteSlaveHistoryEntry 4 }

f3PtpRemoteSlaveHistorySyncMsgsGen OBJECT-TYPE
    SYNTAX      PerfCounter64
    MAX-ACCESS  read-only
    STATUS      current
    DESCRIPTION
            "Total Sync messages generated."
    ::= { f3PtpRemoteSlaveHistoryEntry 5 }

f3PtpRemoteSlaveHistoryDelayRspMsgsGen OBJECT-TYPE
    SYNTAX      PerfCounter64
    MAX-ACCESS  read-only
    STATUS      current
    DESCRIPTION
            "Total Delay Response messages generated."
    ::= { f3PtpRemoteSlaveHistoryEntry 6 }

f3PtpRemoteSlaveHistoryAnnounceMsgsGen OBJECT-TYPE
    SYNTAX      PerfCounter64
    MAX-ACCESS  read-only
    STATUS      current
    DESCRIPTION
            "Total Announce messages generated."
    ::= { f3PtpRemoteSlaveHistoryEntry 7 }

f3PtpRemoteSlaveHistorySignallingMsgsGen OBJECT-TYPE
    SYNTAX      PerfCounter64
    MAX-ACCESS  read-only
    STATUS      current
    DESCRIPTION
            "Total Signalling messages generated."
    ::= { f3PtpRemoteSlaveHistoryEntry 8 }

f3PtpRemoteSlaveHistoryDelayReqMsgsRx OBJECT-TYPE
    SYNTAX      PerfCounter64
    MAX-ACCESS  read-only
    STATUS      current
    DESCRIPTION
            "Total Delay Request messages received."
    ::= { f3PtpRemoteSlaveHistoryEntry 9 }

f3PtpRemoteSlaveHistorySignallingMsgsRx OBJECT-TYPE
    SYNTAX      PerfCounter64
    MAX-ACCESS  read-only
    STATUS      current
    DESCRIPTION
            "Total Signalling messages received."
    ::= { f3PtpRemoteSlaveHistoryEntry 10 }

f3PtpRemoteSlaveHistoryDelayReqMsgsDropped OBJECT-TYPE
    SYNTAX      PerfCounter64
    MAX-ACCESS  read-only
    STATUS      current
    DESCRIPTION
            "Total Delay Request messages dropped."
    ::= { f3PtpRemoteSlaveHistoryEntry 11 }

f3PtpRemoteSlaveHistoryInvalidTLVLenDiscards OBJECT-TYPE
    SYNTAX      PerfCounter64
    MAX-ACCESS  read-only
    STATUS      current
    DESCRIPTION
            "Total number of PTP messages discarded due to invalid PTP TLV length."
    ::= { f3PtpRemoteSlaveHistoryEntry 12 }

f3PtpRemoteSlaveHistoryInvalidTLVTypeDiscards OBJECT-TYPE
    SYNTAX      PerfCounter64
    MAX-ACCESS  read-only
    STATUS      current
    DESCRIPTION
            "Total number of PTP messages discarded due to invalid PTP TLV type."
    ::= { f3PtpRemoteSlaveHistoryEntry 13 }

f3PtpRemoteSlaveHistoryTimesSyncLeaseExp OBJECT-TYPE
    SYNTAX      PerfCounter64
    MAX-ACCESS  read-only
    STATUS      current
    DESCRIPTION
            "Count of Sync service lease duration expired events."
    ::= { f3PtpRemoteSlaveHistoryEntry 14 }

f3PtpRemoteSlaveHistoryTimesDelayRspLeaseExp OBJECT-TYPE
    SYNTAX      PerfCounter64
    MAX-ACCESS  read-only
    STATUS      current
    DESCRIPTION
            "Count of Delay Response service lease duration expired events."
    ::= { f3PtpRemoteSlaveHistoryEntry 15 }

f3PtpRemoteSlaveHistoryTimesAnnounceLeaseExp OBJECT-TYPE
    SYNTAX      PerfCounter64
    MAX-ACCESS  read-only
    STATUS      current
    DESCRIPTION
            "Count of Announce service lease duration expired events."
    ::= { f3PtpRemoteSlaveHistoryEntry 16 }

--
-- Remote Slave Threshold Table
--
f3PtpRemoteSlaveThresholdTable OBJECT-TYPE
    SYNTAX      SEQUENCE OF F3PtpRemoteSlaveThresholdEntry
    MAX-ACCESS  not-accessible
    STATUS      current
    DESCRIPTION
            "A table of entries that allow manageability of 
             Master Clock Interface Thresholds."
    ::= { f3PtpPerformanceObjects 18 }

f3PtpRemoteSlaveThresholdEntry OBJECT-TYPE
    SYNTAX      F3PtpRemoteSlaveThresholdEntry
    MAX-ACCESS  not-accessible
    STATUS      current
    DESCRIPTION
            "A conceptual row in the f3PtpRemoteSlaveThresholdTable."
    INDEX { neIndex, f3PtpBCIndex, f3PtpMCIIndex, f3PtpRemoteSlaveStatsSlaveType, f3PtpRemoteSlaveStatsSlaveIndex, 
            f3PtpRemoteSlaveStatsIndex, f3PtpRemoteSlaveThresholdIndex }
    ::= { f3PtpRemoteSlaveThresholdTable 1 }

F3PtpRemoteSlaveThresholdEntry ::= SEQUENCE {
    f3PtpRemoteSlaveThresholdIndex       Integer32,
    f3PtpRemoteSlaveThresholdInterval    CmPmIntervalType,
    f3PtpRemoteSlaveThresholdVariable    VariablePointer,
    f3PtpRemoteSlaveThresholdValueLo     Unsigned32,
    f3PtpRemoteSlaveThresholdValueHi     Unsigned32,
    f3PtpRemoteSlaveThresholdMonValue    PerfCounter64
}

f3PtpRemoteSlaveThresholdIndex OBJECT-TYPE
    SYNTAX     Integer32 (1..65535)
    MAX-ACCESS not-accessible
    STATUS     current
    DESCRIPTION
        "An index that uniquely identifies an entry in the
        f3PtpRemoteSlaveThresholdTable."
    ::= { f3PtpRemoteSlaveThresholdEntry 1 }

f3PtpRemoteSlaveThresholdInterval OBJECT-TYPE
    SYNTAX     CmPmIntervalType
    MAX-ACCESS read-only
    STATUS     current
    DESCRIPTION
        "The interval over which monitored value is
        sampled and compared with the specified threshold."
    ::= { f3PtpRemoteSlaveThresholdEntry 2 }

f3PtpRemoteSlaveThresholdVariable OBJECT-TYPE
    SYNTAX     VariablePointer
    MAX-ACCESS read-only
    STATUS     current
    DESCRIPTION
        "The object identifier of the particular variable to be
        sampled."
    ::= { f3PtpRemoteSlaveThresholdEntry 3 }

f3PtpRemoteSlaveThresholdValueLo OBJECT-TYPE
    SYNTAX     Unsigned32
    MAX-ACCESS read-write
    STATUS     current
    DESCRIPTION
        "Lower 32 bits of the threshold value."
    ::= { f3PtpRemoteSlaveThresholdEntry 4 }

f3PtpRemoteSlaveThresholdValueHi OBJECT-TYPE
    SYNTAX     Unsigned32
    MAX-ACCESS read-write
    STATUS     current
    DESCRIPTION
        "Higher 32 bits of the threshold value."
    ::= { f3PtpRemoteSlaveThresholdEntry 5 }

f3PtpRemoteSlaveThresholdMonValue OBJECT-TYPE
    SYNTAX     PerfCounter64
    MAX-ACCESS read-only
    STATUS     current
    DESCRIPTION
        "Monitored value corresponding to f3PtpRemoteSlaveThresholdVariable."
    ::= { f3PtpRemoteSlaveThresholdEntry 6 }

--
-- Traffic Port PTP Flow Point Current Statistics Table
--
f3PtpTrafficPortFlowPointStatsTable OBJECT-TYPE
    SYNTAX      SEQUENCE OF F3PtpTrafficPortFlowPointStatsEntry
   MAX-ACCESS  not-accessible
    STATUS      current
    DESCRIPTION
            "A collection of Traffic Port PTP Flow Point statistics.  
             These reflect the current data."
    ::= { f3PtpPerformanceObjects 19 }

f3PtpTrafficPortFlowPointStatsEntry OBJECT-TYPE
    SYNTAX      F3PtpTrafficPortFlowPointStatsEntry 
   MAX-ACCESS  not-accessible
    STATUS      current
    DESCRIPTION
            "A conceptual row in the f3PtpTrafficPortFlowPointStatsTable.
             Entries exist in this table for each Traffic Port Flow Point."
    INDEX { neIndex, shelfIndex, slotIndex, cmEthernetTrafficPortIndex, 
            f3PtpTrafficPortFlowPointIndex, f3PtpTrafficPortFlowPointStatsIndex }
    ::= { f3PtpTrafficPortFlowPointStatsTable 1 }

F3PtpTrafficPortFlowPointStatsEntry ::= SEQUENCE {
    f3PtpTrafficPortFlowPointStatsIndex                  Integer32,
    f3PtpTrafficPortFlowPointStatsIntervalType           CmPmIntervalType,
    f3PtpTrafficPortFlowPointStatsValid                  TruthValue,
    f3PtpTrafficPortFlowPointStatsAction                 CmPmBinAction,
    f3PtpTrafficPortFlowPointStatsAnnouncesRx            PerfCounter64,
    f3PtpTrafficPortFlowPointStatsAnnouncesTx            PerfCounter64,
    f3PtpTrafficPortFlowPointStatsSyncsRx                PerfCounter64,
    f3PtpTrafficPortFlowPointStatsSyncsTx                PerfCounter64,
    f3PtpTrafficPortFlowPointStatsFollowupsRx            PerfCounter64,
    f3PtpTrafficPortFlowPointStatsFollowupsTx            PerfCounter64,
    f3PtpTrafficPortFlowPointStatsDelayReqsRx            PerfCounter64,
    f3PtpTrafficPortFlowPointStatsDelayReqsTx            PerfCounter64,
    f3PtpTrafficPortFlowPointStatsDelayRspsRx            PerfCounter64,
    f3PtpTrafficPortFlowPointStatsDelayRspsTx            PerfCounter64,
    f3PtpTrafficPortFlowPointStatsPDelayReqsRx           PerfCounter64,
    f3PtpTrafficPortFlowPointStatsPDelayReqsTx           PerfCounter64,
    f3PtpTrafficPortFlowPointStatsPDelayRspsRx           PerfCounter64,
    f3PtpTrafficPortFlowPointStatsPDelayRspsTx           PerfCounter64,
    f3PtpTrafficPortFlowPointStatsPDelayRspFollowupsRx   PerfCounter64,
    f3PtpTrafficPortFlowPointStatsPDelayRspFollowupsTx   PerfCounter64,
    f3PtpTrafficPortFlowPointStatsSignalingRx            PerfCounter64,
    f3PtpTrafficPortFlowPointStatsSignalingTx            PerfCounter64,
    f3PtpTrafficPortFlowPointStatsMgmtFramesRx           PerfCounter64,
    f3PtpTrafficPortFlowPointStatsMgmtFramesTx           PerfCounter64,
    f3PtpTrafficPortFlowPointStatsPtpUnknownsRx          PerfCounter64,
    f3PtpTrafficPortFlowPointStatsPtpUnknownsTx          PerfCounter64,
    f3PtpTrafficPortFlowPointStatsMinSyncResTime         Unsigned32,
    f3PtpTrafficPortFlowPointStatsMaxSyncResTime         Unsigned32,
    f3PtpTrafficPortFlowPointStatsAvgSyncResTime         Unsigned32,
    f3PtpTrafficPortFlowPointStatsMinDelayReqResTime     Unsigned32,
    f3PtpTrafficPortFlowPointStatsMaxDelayReqResTime     Unsigned32,
    f3PtpTrafficPortFlowPointStatsAvgDelayReqResTime     Unsigned32,
    f3PtpTrafficPortFlowPointStatsMinPDelayReqResTime    Unsigned32,
    f3PtpTrafficPortFlowPointStatsMaxPDelayReqResTime    Unsigned32,
    f3PtpTrafficPortFlowPointStatsAvgPDelayReqResTime    Unsigned32,
    f3PtpTrafficPortFlowPointStatsMinPDelayRspResTime    Unsigned32,
    f3PtpTrafficPortFlowPointStatsMaxPDelayRspResTime    Unsigned32,
    f3PtpTrafficPortFlowPointStatsAvgPDelayRspResTime    Unsigned32,
    f3PtpTrafficPortFlowPointStatsDestMciNoMatchDiscards PerfCounter64,
    f3PtpTrafficPortFlowPointStatsTagNoMatchDiscards     PerfCounter64
}

f3PtpTrafficPortFlowPointStatsIndex OBJECT-TYPE
    SYNTAX      Integer32 (1..4)
   MAX-ACCESS  not-accessible 
    STATUS      current
    DESCRIPTION
            "An arbitrary integer index value used to uniquely identify
            this Traffic Port PTP Flow Point statistics entry. 
            1 - 15min
            2 - 1day
            3 - rollover
            4 - 5min"
    ::= { f3PtpTrafficPortFlowPointStatsEntry 1 }

f3PtpTrafficPortFlowPointStatsIntervalType OBJECT-TYPE
    SYNTAX      CmPmIntervalType
   MAX-ACCESS  read-only
    STATUS      current
    DESCRIPTION
            "Indicates the type of collection, i.e. whether it is
             15 Min, 1 Day or rollover."
    ::= { f3PtpTrafficPortFlowPointStatsEntry 2 }

f3PtpTrafficPortFlowPointStatsValid OBJECT-TYPE
    SYNTAX      TruthValue
   MAX-ACCESS  read-only
    STATUS      current
    DESCRIPTION
            "Indicates the validity of the bin."
    ::= { f3PtpTrafficPortFlowPointStatsEntry 3 }

f3PtpTrafficPortFlowPointStatsAction OBJECT-TYPE
    SYNTAX      CmPmBinAction
   MAX-ACCESS  read-write
    STATUS      current
    DESCRIPTION
            "Allows the Manager to clear the bin."
    ::= { f3PtpTrafficPortFlowPointStatsEntry 4 }

f3PtpTrafficPortFlowPointStatsAnnouncesRx OBJECT-TYPE
     SYNTAX     PerfCounter64
    MAX-ACCESS read-only
     STATUS     current
     DESCRIPTION
         "Number of PTP Announce messages received on the PTP Flow Point."
     ::= { f3PtpTrafficPortFlowPointStatsEntry 5 }

f3PtpTrafficPortFlowPointStatsAnnouncesTx OBJECT-TYPE
     SYNTAX     PerfCounter64
    MAX-ACCESS read-only
     STATUS     current
     DESCRIPTION
         "Number of Announce Messages transmitted on the PTP Flow Point.
          This object is applicable for transparent clocks."
     ::= { f3PtpTrafficPortFlowPointStatsEntry 6 }

f3PtpTrafficPortFlowPointStatsSyncsRx OBJECT-TYPE
     SYNTAX     PerfCounter64
    MAX-ACCESS read-only
     STATUS     current
     DESCRIPTION
         "Number of Sync Messages received on the PTP Flow Point."
     ::= { f3PtpTrafficPortFlowPointStatsEntry 7 }

f3PtpTrafficPortFlowPointStatsSyncsTx OBJECT-TYPE
     SYNTAX     PerfCounter64
    MAX-ACCESS read-only
     STATUS     current
     DESCRIPTION
         "Number of Sync Messages transmitted on the PTP Flow Point.
          This object is applicable for transparent clocks."
     ::= { f3PtpTrafficPortFlowPointStatsEntry 8 }

f3PtpTrafficPortFlowPointStatsFollowupsRx OBJECT-TYPE
     SYNTAX     PerfCounter64
    MAX-ACCESS read-only
     STATUS     current
     DESCRIPTION
         "Number of Follow up Messages received on the PTP Flow Point."
     ::= { f3PtpTrafficPortFlowPointStatsEntry 9 }

f3PtpTrafficPortFlowPointStatsFollowupsTx OBJECT-TYPE
     SYNTAX     PerfCounter64
    MAX-ACCESS read-only
     STATUS     current
     DESCRIPTION
         "Number of Follow up Messages transmitted on the PTP Flow Point."
     ::= { f3PtpTrafficPortFlowPointStatsEntry 10 }

f3PtpTrafficPortFlowPointStatsDelayReqsRx OBJECT-TYPE
     SYNTAX     PerfCounter64
    MAX-ACCESS read-only
     STATUS     current
     DESCRIPTION
         "Number of Delay Request Messages received on the PTP Flow Point."
     ::= { f3PtpTrafficPortFlowPointStatsEntry 11 }

f3PtpTrafficPortFlowPointStatsDelayReqsTx OBJECT-TYPE
     SYNTAX     PerfCounter64
    MAX-ACCESS read-only
     STATUS     current
     DESCRIPTION
         "Number of Delay Request Messages transmitted on the PTP Flow Point."
     ::= { f3PtpTrafficPortFlowPointStatsEntry 12 }

f3PtpTrafficPortFlowPointStatsDelayRspsRx OBJECT-TYPE
     SYNTAX     PerfCounter64
    MAX-ACCESS read-only
     STATUS     current
     DESCRIPTION
         "Number of Delay Response Messages received on the PTP Flow Point."
     ::= { f3PtpTrafficPortFlowPointStatsEntry 13 }

f3PtpTrafficPortFlowPointStatsDelayRspsTx OBJECT-TYPE
     SYNTAX     PerfCounter64
    MAX-ACCESS read-only
     STATUS     current
     DESCRIPTION
         "Number of Delay Response Messages transmitted on the PTP Flow Point."
     ::= { f3PtpTrafficPortFlowPointStatsEntry 14 }

f3PtpTrafficPortFlowPointStatsPDelayReqsRx OBJECT-TYPE
     SYNTAX     PerfCounter64
    MAX-ACCESS read-only
     STATUS     current
     DESCRIPTION
         "Number of Peer Delay Request Messages received on the PTP Flow Point."
     ::= { f3PtpTrafficPortFlowPointStatsEntry 15 }

f3PtpTrafficPortFlowPointStatsPDelayReqsTx OBJECT-TYPE
     SYNTAX     PerfCounter64
    MAX-ACCESS read-only
     STATUS     current
     DESCRIPTION
         "Number of Peer Delay Request Messages transmitted on the PTP Flow Point."
     ::= { f3PtpTrafficPortFlowPointStatsEntry 16 }

f3PtpTrafficPortFlowPointStatsPDelayRspsRx OBJECT-TYPE
     SYNTAX     PerfCounter64
    MAX-ACCESS read-only
     STATUS     current
     DESCRIPTION
         "Number of Peer Delay Response Messages received on the PTP Flow Point."
     ::= { f3PtpTrafficPortFlowPointStatsEntry 17 }

f3PtpTrafficPortFlowPointStatsPDelayRspsTx OBJECT-TYPE
     SYNTAX     PerfCounter64
    MAX-ACCESS read-only
     STATUS     current
     DESCRIPTION
         "Number of Peer Delay Response Messages transmitted on the PTP Flow Point."
     ::= { f3PtpTrafficPortFlowPointStatsEntry 18 }

f3PtpTrafficPortFlowPointStatsPDelayRspFollowupsRx OBJECT-TYPE
     SYNTAX     PerfCounter64
    MAX-ACCESS read-only
     STATUS     current
     DESCRIPTION
         "Number of Peer Delay Response Followup Messages received on the PTP Flow Point."
     ::= { f3PtpTrafficPortFlowPointStatsEntry 19 }

f3PtpTrafficPortFlowPointStatsPDelayRspFollowupsTx OBJECT-TYPE
     SYNTAX     PerfCounter64
    MAX-ACCESS read-only
     STATUS     current
     DESCRIPTION
         "Number of Peer Delay Response Followup Messages transmitted on the PTP Flow Point."
     ::= { f3PtpTrafficPortFlowPointStatsEntry 20 }

f3PtpTrafficPortFlowPointStatsSignalingRx OBJECT-TYPE
     SYNTAX     PerfCounter64
    MAX-ACCESS read-only
     STATUS     current
     DESCRIPTION
         "Number of PTP Signaling Messages received on the PTP Flow Point."
     ::= { f3PtpTrafficPortFlowPointStatsEntry 21 }

f3PtpTrafficPortFlowPointStatsSignalingTx OBJECT-TYPE
     SYNTAX     PerfCounter64
    MAX-ACCESS read-only
     STATUS     current
     DESCRIPTION
         "Number of PTP Signaling Messages Messages transmitted on the PTP Flow Point."
     ::= { f3PtpTrafficPortFlowPointStatsEntry 22 }

f3PtpTrafficPortFlowPointStatsMgmtFramesRx OBJECT-TYPE
     SYNTAX     PerfCounter64
    MAX-ACCESS read-only
     STATUS     current
     DESCRIPTION
         "Number of PTP Management Frames received on the PTP Flow Point."
     ::= { f3PtpTrafficPortFlowPointStatsEntry 23 }

f3PtpTrafficPortFlowPointStatsMgmtFramesTx OBJECT-TYPE
     SYNTAX     PerfCounter64
    MAX-ACCESS read-only
     STATUS     current
     DESCRIPTION
         "Number of PTP Management Frames Messages transmitted on the PTP Flow Point."
     ::= { f3PtpTrafficPortFlowPointStatsEntry 24 }

f3PtpTrafficPortFlowPointStatsPtpUnknownsRx OBJECT-TYPE
     SYNTAX     PerfCounter64
    MAX-ACCESS read-only
     STATUS     current
     DESCRIPTION
         "Number of Unknown PTP Messages received on the PTP Flow Point."
     ::= { f3PtpTrafficPortFlowPointStatsEntry 25 }

f3PtpTrafficPortFlowPointStatsPtpUnknownsTx OBJECT-TYPE
     SYNTAX     PerfCounter64
    MAX-ACCESS read-only
     STATUS     current
     DESCRIPTION
         "Number of Unknown PTP Messages transmitted on the PTP Flow Point."
     ::= { f3PtpTrafficPortFlowPointStatsEntry 26 }

f3PtpTrafficPortFlowPointStatsMinSyncResTime OBJECT-TYPE
     SYNTAX     Unsigned32
    MAX-ACCESS read-only
     STATUS     current
     DESCRIPTION
         "The minimum residence time for PTP Sync messages."
     ::= { f3PtpTrafficPortFlowPointStatsEntry 27 }

f3PtpTrafficPortFlowPointStatsMaxSyncResTime OBJECT-TYPE
     SYNTAX     Unsigned32
    MAX-ACCESS read-only
     STATUS     current
     DESCRIPTION
         "The maximum residence time for PTP Sync messages."
     ::= { f3PtpTrafficPortFlowPointStatsEntry 28 }

f3PtpTrafficPortFlowPointStatsAvgSyncResTime OBJECT-TYPE
     SYNTAX     Unsigned32
    MAX-ACCESS read-only
     STATUS     current
     DESCRIPTION
         "The average residence time for PTP Sync messages."
     ::= { f3PtpTrafficPortFlowPointStatsEntry 29 }

f3PtpTrafficPortFlowPointStatsMinDelayReqResTime OBJECT-TYPE
     SYNTAX     Unsigned32
    MAX-ACCESS read-only
     STATUS     current
     DESCRIPTION
         "The minimum residence time for PTP Delay Request messages."
     ::= { f3PtpTrafficPortFlowPointStatsEntry 30 }

f3PtpTrafficPortFlowPointStatsMaxDelayReqResTime OBJECT-TYPE
     SYNTAX     Unsigned32
    MAX-ACCESS read-only
     STATUS     current
     DESCRIPTION
         "The maximum residence time for PTP Delay Request messages."
     ::= { f3PtpTrafficPortFlowPointStatsEntry 31 }

f3PtpTrafficPortFlowPointStatsAvgDelayReqResTime OBJECT-TYPE
     SYNTAX     Unsigned32
    MAX-ACCESS read-only
     STATUS     current
     DESCRIPTION
         "The average residence time for PTP Delay Request messages."
     ::= { f3PtpTrafficPortFlowPointStatsEntry 32 }

f3PtpTrafficPortFlowPointStatsMinPDelayReqResTime OBJECT-TYPE
     SYNTAX     Unsigned32
    MAX-ACCESS read-only
     STATUS     current
     DESCRIPTION
         "The minimum residence time for PTP Peer Delay Request messages."
     ::= { f3PtpTrafficPortFlowPointStatsEntry 33 }

f3PtpTrafficPortFlowPointStatsMaxPDelayReqResTime OBJECT-TYPE
     SYNTAX     Unsigned32
    MAX-ACCESS read-only
     STATUS     current
     DESCRIPTION
         "The maximum residence time for PTP Peer Delay Request messages."
     ::= { f3PtpTrafficPortFlowPointStatsEntry 34 }

f3PtpTrafficPortFlowPointStatsAvgPDelayReqResTime OBJECT-TYPE
     SYNTAX     Unsigned32
    MAX-ACCESS read-only
     STATUS     current
     DESCRIPTION
         "The average residence time for PTP Peer Delay Request messages."
     ::= { f3PtpTrafficPortFlowPointStatsEntry 35 }

f3PtpTrafficPortFlowPointStatsMinPDelayRspResTime OBJECT-TYPE
     SYNTAX     Unsigned32
    MAX-ACCESS read-only
     STATUS     current
     DESCRIPTION
         "The minimum residence time for PTP Peer Delay Response messages."
     ::= { f3PtpTrafficPortFlowPointStatsEntry 36 }

f3PtpTrafficPortFlowPointStatsMaxPDelayRspResTime OBJECT-TYPE
     SYNTAX     Unsigned32
    MAX-ACCESS read-only
     STATUS     current
     DESCRIPTION
         "The maximum residence time for PTP Peer Delay Response messages."
     ::= { f3PtpTrafficPortFlowPointStatsEntry 37 }

f3PtpTrafficPortFlowPointStatsAvgPDelayRspResTime OBJECT-TYPE
     SYNTAX     Unsigned32
    MAX-ACCESS read-only
     STATUS     current
     DESCRIPTION
         "The average residence time for PTP Peer Delay Response messages."
     ::= { f3PtpTrafficPortFlowPointStatsEntry 38 }

f3PtpTrafficPortFlowPointStatsDestMciNoMatchDiscards OBJECT-TYPE
     SYNTAX     PerfCounter64
    MAX-ACCESS read-only
     STATUS     current
     DESCRIPTION
         "The dest MCI no match discards messages."
     ::= { f3PtpTrafficPortFlowPointStatsEntry 39 }


f3PtpTrafficPortFlowPointStatsTagNoMatchDiscards OBJECT-TYPE
     SYNTAX     PerfCounter64
    MAX-ACCESS read-only
     STATUS     current
     DESCRIPTION
         "PTP frames discarded due to tag mismatch. For example, eth-multicast FP is tagged,
         then untagged non-forwardable PTP frames shall be discarded."
     ::= { f3PtpTrafficPortFlowPointStatsEntry 40 }

--
-- Traffic Port PTP Flow Point History Table
--
f3PtpTrafficPortFlowPointHistoryTable OBJECT-TYPE
    SYNTAX      SEQUENCE OF F3PtpTrafficPortFlowPointHistoryEntry
   MAX-ACCESS  not-accessible
    STATUS      current
    DESCRIPTION
            "A collection of Traffic Port PTP Flow Point history statistics.  
             These reflect the history data."
    ::= { f3PtpPerformanceObjects 20 }

f3PtpTrafficPortFlowPointHistoryEntry OBJECT-TYPE
    SYNTAX      F3PtpTrafficPortFlowPointHistoryEntry 
   MAX-ACCESS  not-accessible
    STATUS      current
    DESCRIPTION
            "A conceptual row in the f3PtpTrafficPortFlowPointHistoryTable.
             Entries exist in this table for each Traffic Port Flow Point."
    INDEX { neIndex, shelfIndex, slotIndex, cmEthernetTrafficPortIndex, 
            f3PtpTrafficPortFlowPointIndex, f3PtpTrafficPortFlowPointStatsIndex, 
            f3PtpTrafficPortFlowPointHistoryIndex }
    ::= { f3PtpTrafficPortFlowPointHistoryTable 1 }

F3PtpTrafficPortFlowPointHistoryEntry ::= SEQUENCE {
    f3PtpTrafficPortFlowPointHistoryIndex                  Integer32,
    f3PtpTrafficPortFlowPointHistoryTime                   DateAndTime,
    f3PtpTrafficPortFlowPointHistoryValid                  TruthValue,
    f3PtpTrafficPortFlowPointHistoryAction                 CmPmBinAction,
    f3PtpTrafficPortFlowPointHistoryAnnouncesRx            PerfCounter64,
    f3PtpTrafficPortFlowPointHistoryAnnouncesTx            PerfCounter64,
    f3PtpTrafficPortFlowPointHistorySyncsRx                PerfCounter64,
    f3PtpTrafficPortFlowPointHistorySyncsTx                PerfCounter64,
    f3PtpTrafficPortFlowPointHistoryFollowupsRx            PerfCounter64,
    f3PtpTrafficPortFlowPointHistoryFollowupsTx            PerfCounter64,
    f3PtpTrafficPortFlowPointHistoryDelayReqsRx            PerfCounter64,
    f3PtpTrafficPortFlowPointHistoryDelayReqsTx            PerfCounter64,
    f3PtpTrafficPortFlowPointHistoryDelayRspsRx            PerfCounter64,
    f3PtpTrafficPortFlowPointHistoryDelayRspsTx            PerfCounter64,
    f3PtpTrafficPortFlowPointHistoryPDelayReqsRx           PerfCounter64,
    f3PtpTrafficPortFlowPointHistoryPDelayReqsTx           PerfCounter64,
    f3PtpTrafficPortFlowPointHistoryPDelayRspsRx           PerfCounter64,
    f3PtpTrafficPortFlowPointHistoryPDelayRspsTx           PerfCounter64,
    f3PtpTrafficPortFlowPointHistoryPDelayRspFollowupsRx   PerfCounter64,
    f3PtpTrafficPortFlowPointHistoryPDelayRspFollowupsTx   PerfCounter64,
    f3PtpTrafficPortFlowPointHistorySignalingRx            PerfCounter64,
    f3PtpTrafficPortFlowPointHistorySignalingTx            PerfCounter64,
    f3PtpTrafficPortFlowPointHistoryMgmtFramesRx           PerfCounter64,
    f3PtpTrafficPortFlowPointHistoryMgmtFramesTx           PerfCounter64,
    f3PtpTrafficPortFlowPointHistoryPtpUnknownsRx          PerfCounter64,
    f3PtpTrafficPortFlowPointHistoryPtpUnknownsTx          PerfCounter64,
    f3PtpTrafficPortFlowPointHistoryMinSyncResTime         Unsigned32,
    f3PtpTrafficPortFlowPointHistoryMaxSyncResTime         Unsigned32,
    f3PtpTrafficPortFlowPointHistoryAvgSyncResTime         Unsigned32,
    f3PtpTrafficPortFlowPointHistoryMinDelayReqResTime     Unsigned32,
    f3PtpTrafficPortFlowPointHistoryMaxDelayReqResTime     Unsigned32,
    f3PtpTrafficPortFlowPointHistoryAvgDelayReqResTime     Unsigned32,
    f3PtpTrafficPortFlowPointHistoryMinPDelayReqResTime    Unsigned32,
    f3PtpTrafficPortFlowPointHistoryMaxPDelayReqResTime    Unsigned32,
    f3PtpTrafficPortFlowPointHistoryAvgPDelayReqResTime    Unsigned32,
    f3PtpTrafficPortFlowPointHistoryMinPDelayRspResTime    Unsigned32,
    f3PtpTrafficPortFlowPointHistoryMaxPDelayRspResTime    Unsigned32,
    f3PtpTrafficPortFlowPointHistoryAvgPDelayRspResTime    Unsigned32,
    f3PtpTrafficPortFlowPointHistoryDestMciNoMatchDiscards PerfCounter64,
    f3PtpTrafficPortFlowPointHistoryTagNoMatchDiscards     PerfCounter64
}

f3PtpTrafficPortFlowPointHistoryIndex OBJECT-TYPE
    SYNTAX      Integer32 (1..32)
   MAX-ACCESS  not-accessible 
    STATUS      current
    DESCRIPTION
            "An arbitrary integer index value used to uniquely identify
            this Ethernet Traffic Port PTP Flow point PM history entry."
    ::= { f3PtpTrafficPortFlowPointHistoryEntry 1 }

f3PtpTrafficPortFlowPointHistoryTime OBJECT-TYPE
    SYNTAX      DateAndTime
   MAX-ACCESS  read-only
    STATUS      current
    DESCRIPTION
            "Indicates the time of history bin creation." 
    ::= { f3PtpTrafficPortFlowPointHistoryEntry 2 }

f3PtpTrafficPortFlowPointHistoryValid OBJECT-TYPE
    SYNTAX      TruthValue
   MAX-ACCESS  read-only
    STATUS      current
    DESCRIPTION
            "Indicates the validity of the bin."
    ::= { f3PtpTrafficPortFlowPointHistoryEntry 3 }

f3PtpTrafficPortFlowPointHistoryAction OBJECT-TYPE
    SYNTAX      CmPmBinAction
   MAX-ACCESS  read-write
    STATUS      current
    DESCRIPTION
            "Allows the Manager to clear the bin."
    ::= { f3PtpTrafficPortFlowPointHistoryEntry 4 }

f3PtpTrafficPortFlowPointHistoryAnnouncesRx OBJECT-TYPE
     SYNTAX     PerfCounter64
    MAX-ACCESS read-only
     STATUS     current
     DESCRIPTION
         "Number of PTP Announce messages received on the PTP Flow Point."
     ::= { f3PtpTrafficPortFlowPointHistoryEntry 5 }

f3PtpTrafficPortFlowPointHistoryAnnouncesTx OBJECT-TYPE
     SYNTAX     PerfCounter64
    MAX-ACCESS read-only
     STATUS     current
     DESCRIPTION
         "Number of Announce Messages transmitted on the PTP Flow Point.
          This object is applicable for transparent clocks."
     ::= { f3PtpTrafficPortFlowPointHistoryEntry 6 }

f3PtpTrafficPortFlowPointHistorySyncsRx OBJECT-TYPE
     SYNTAX     PerfCounter64
    MAX-ACCESS read-only
     STATUS     current
     DESCRIPTION
         "Number of Sync Messages received on the PTP Flow Point."
     ::= { f3PtpTrafficPortFlowPointHistoryEntry 7 }

f3PtpTrafficPortFlowPointHistorySyncsTx OBJECT-TYPE
     SYNTAX     PerfCounter64
    MAX-ACCESS read-only
     STATUS     current
     DESCRIPTION
         "Number of Sync Messages transmitted on the PTP Flow Point.
          This object is applicable for transparent clocks."
     ::= { f3PtpTrafficPortFlowPointHistoryEntry 8 }

f3PtpTrafficPortFlowPointHistoryFollowupsRx OBJECT-TYPE
     SYNTAX     PerfCounter64
    MAX-ACCESS read-only
     STATUS     current
     DESCRIPTION
         "Number of Follow up Messages received on the PTP Flow Point."
     ::= { f3PtpTrafficPortFlowPointHistoryEntry 9 }

f3PtpTrafficPortFlowPointHistoryFollowupsTx OBJECT-TYPE
     SYNTAX     PerfCounter64
    MAX-ACCESS read-only
     STATUS     current
     DESCRIPTION
         "Number of Follow up Messages transmitted on the PTP Flow Point."
     ::= { f3PtpTrafficPortFlowPointHistoryEntry 10 }

f3PtpTrafficPortFlowPointHistoryDelayReqsRx OBJECT-TYPE
     SYNTAX     PerfCounter64
    MAX-ACCESS read-only
     STATUS     current
     DESCRIPTION
         "Number of Delay Request Messages received on the PTP Flow Point."
     ::= { f3PtpTrafficPortFlowPointHistoryEntry 11 }

f3PtpTrafficPortFlowPointHistoryDelayReqsTx OBJECT-TYPE
     SYNTAX     PerfCounter64
    MAX-ACCESS read-only
     STATUS     current
     DESCRIPTION
         "Number of Delay Request Messages transmitted on the PTP Flow Point."
     ::= { f3PtpTrafficPortFlowPointHistoryEntry 12 }

f3PtpTrafficPortFlowPointHistoryDelayRspsRx OBJECT-TYPE
     SYNTAX     PerfCounter64
    MAX-ACCESS read-only
     STATUS     current
     DESCRIPTION
         "Number of Delay Response Messages received on the PTP Flow Point."
     ::= { f3PtpTrafficPortFlowPointHistoryEntry 13 }

f3PtpTrafficPortFlowPointHistoryDelayRspsTx OBJECT-TYPE
     SYNTAX     PerfCounter64
    MAX-ACCESS read-only
     STATUS     current
     DESCRIPTION
         "Number of Delay Response Messages transmitted on the PTP Flow Point."
     ::= { f3PtpTrafficPortFlowPointHistoryEntry 14 }

f3PtpTrafficPortFlowPointHistoryPDelayReqsRx OBJECT-TYPE
     SYNTAX     PerfCounter64
    MAX-ACCESS read-only
     STATUS     current
     DESCRIPTION
         "Number of Peer Delay Request Messages received on the PTP Flow Point."
     ::= { f3PtpTrafficPortFlowPointHistoryEntry 15 }

f3PtpTrafficPortFlowPointHistoryPDelayReqsTx OBJECT-TYPE
     SYNTAX     PerfCounter64
    MAX-ACCESS read-only
     STATUS     current
     DESCRIPTION
         "Number of Peer Delay Request Messages transmitted on the PTP Flow Point."
     ::= { f3PtpTrafficPortFlowPointHistoryEntry 16 }

f3PtpTrafficPortFlowPointHistoryPDelayRspsRx OBJECT-TYPE
     SYNTAX     PerfCounter64
    MAX-ACCESS read-only
     STATUS     current
     DESCRIPTION
         "Number of Peer Delay Response Messages received on the PTP Flow Point."
     ::= { f3PtpTrafficPortFlowPointHistoryEntry 17 }

f3PtpTrafficPortFlowPointHistoryPDelayRspsTx OBJECT-TYPE
     SYNTAX     PerfCounter64
    MAX-ACCESS read-only
     STATUS     current
     DESCRIPTION
         "Number of Peer Delay Response Messages transmitted on the PTP Flow Point."
     ::= { f3PtpTrafficPortFlowPointHistoryEntry 18 }

f3PtpTrafficPortFlowPointHistoryPDelayRspFollowupsRx OBJECT-TYPE
     SYNTAX     PerfCounter64
    MAX-ACCESS read-only
     STATUS     current
     DESCRIPTION
         "Number of Peer Delay Response Followup Messages received on the PTP Flow Point."
     ::= { f3PtpTrafficPortFlowPointHistoryEntry 19 }

f3PtpTrafficPortFlowPointHistoryPDelayRspFollowupsTx OBJECT-TYPE
     SYNTAX     PerfCounter64
    MAX-ACCESS read-only
     STATUS     current
     DESCRIPTION
         "Number of Peer Delay Response Followup Messages transmitted on the PTP Flow Point."
     ::= { f3PtpTrafficPortFlowPointHistoryEntry 20 }

f3PtpTrafficPortFlowPointHistorySignalingRx OBJECT-TYPE
     SYNTAX     PerfCounter64
    MAX-ACCESS read-only
     STATUS     current
     DESCRIPTION
         "Number of PTP Signaling Messages received on the PTP Flow Point."
     ::= { f3PtpTrafficPortFlowPointHistoryEntry 21 }

f3PtpTrafficPortFlowPointHistorySignalingTx OBJECT-TYPE
     SYNTAX     PerfCounter64
    MAX-ACCESS read-only
     STATUS     current
     DESCRIPTION
         "Number of PTP Signaling Messages Messages transmitted on the PTP Flow Point."
     ::= { f3PtpTrafficPortFlowPointHistoryEntry 22 }

f3PtpTrafficPortFlowPointHistoryMgmtFramesRx OBJECT-TYPE
     SYNTAX     PerfCounter64
    MAX-ACCESS read-only
     STATUS     current
     DESCRIPTION
         "Number of PTP Management Frames received on the PTP Flow Point."
     ::= { f3PtpTrafficPortFlowPointHistoryEntry 23 }

f3PtpTrafficPortFlowPointHistoryMgmtFramesTx OBJECT-TYPE
     SYNTAX     PerfCounter64
    MAX-ACCESS read-only
     STATUS     current
     DESCRIPTION
         "Number of PTP Management Frames Messages transmitted on the PTP Flow Point."
     ::= { f3PtpTrafficPortFlowPointHistoryEntry 24 }

f3PtpTrafficPortFlowPointHistoryPtpUnknownsRx OBJECT-TYPE
     SYNTAX     PerfCounter64
    MAX-ACCESS read-only
     STATUS     current
     DESCRIPTION
         "Number of Unknown PTP Messages received on the PTP Flow Point."
     ::= { f3PtpTrafficPortFlowPointHistoryEntry 25 }

f3PtpTrafficPortFlowPointHistoryPtpUnknownsTx OBJECT-TYPE
     SYNTAX     PerfCounter64
    MAX-ACCESS read-only
     STATUS     current
     DESCRIPTION
         "Number of Unknown PTP Messages transmitted on the PTP Flow Point."
     ::= { f3PtpTrafficPortFlowPointHistoryEntry 26 }

f3PtpTrafficPortFlowPointHistoryMinSyncResTime OBJECT-TYPE
     SYNTAX     Unsigned32
    MAX-ACCESS read-only
     STATUS     current
     DESCRIPTION
         "The minimum residence time for PTP Sync messages."
     ::= { f3PtpTrafficPortFlowPointHistoryEntry 27 }

f3PtpTrafficPortFlowPointHistoryMaxSyncResTime OBJECT-TYPE
     SYNTAX     Unsigned32
    MAX-ACCESS read-only
     STATUS     current
     DESCRIPTION
         "The maximum residence time for PTP Sync messages."
     ::= { f3PtpTrafficPortFlowPointHistoryEntry 28 }

f3PtpTrafficPortFlowPointHistoryAvgSyncResTime OBJECT-TYPE
     SYNTAX     Unsigned32
    MAX-ACCESS read-only
     STATUS     current
     DESCRIPTION
         "The average residence time for PTP Sync messages."
     ::= { f3PtpTrafficPortFlowPointHistoryEntry 29 }

f3PtpTrafficPortFlowPointHistoryMinDelayReqResTime OBJECT-TYPE
     SYNTAX     Unsigned32
    MAX-ACCESS read-only
     STATUS     current
     DESCRIPTION
         "The minimum residence time for PTP Delay Request messages."
     ::= { f3PtpTrafficPortFlowPointHistoryEntry 30 }

f3PtpTrafficPortFlowPointHistoryMaxDelayReqResTime OBJECT-TYPE
     SYNTAX     Unsigned32
    MAX-ACCESS read-only
     STATUS     current
     DESCRIPTION
         "The maximum residence time for PTP Delay Request messages."
     ::= { f3PtpTrafficPortFlowPointHistoryEntry 31 }

f3PtpTrafficPortFlowPointHistoryAvgDelayReqResTime OBJECT-TYPE
     SYNTAX     Unsigned32
    MAX-ACCESS read-only
     STATUS     current
     DESCRIPTION
         "The average residence time for PTP Delay Request messages."
     ::= { f3PtpTrafficPortFlowPointHistoryEntry 32 }

f3PtpTrafficPortFlowPointHistoryMinPDelayReqResTime OBJECT-TYPE
     SYNTAX     Unsigned32
    MAX-ACCESS read-only
     STATUS     current
     DESCRIPTION
         "The minimum residence time for PTP Peer Delay Request messages."
     ::= { f3PtpTrafficPortFlowPointHistoryEntry 33 }

f3PtpTrafficPortFlowPointHistoryMaxPDelayReqResTime OBJECT-TYPE
     SYNTAX     Unsigned32
    MAX-ACCESS read-only
     STATUS     current
     DESCRIPTION
         "The maximum residence time for PTP Peer Delay Request messages."
     ::= { f3PtpTrafficPortFlowPointHistoryEntry 34 }

f3PtpTrafficPortFlowPointHistoryAvgPDelayReqResTime OBJECT-TYPE
     SYNTAX     Unsigned32
    MAX-ACCESS read-only
     STATUS     current
     DESCRIPTION
         "The average residence time for PTP Peer Delay Request messages."
     ::= { f3PtpTrafficPortFlowPointHistoryEntry 35 }

f3PtpTrafficPortFlowPointHistoryMinPDelayRspResTime OBJECT-TYPE
     SYNTAX     Unsigned32
    MAX-ACCESS read-only
     STATUS     current
     DESCRIPTION
         "The minimum residence time for PTP Peer Delay Response messages."
     ::= { f3PtpTrafficPortFlowPointHistoryEntry 36 }

f3PtpTrafficPortFlowPointHistoryMaxPDelayRspResTime OBJECT-TYPE
     SYNTAX     Unsigned32
    MAX-ACCESS read-only
     STATUS     current
     DESCRIPTION
         "The maximum residence time for PTP Peer Delay Response messages."
     ::= { f3PtpTrafficPortFlowPointHistoryEntry 37 }

f3PtpTrafficPortFlowPointHistoryAvgPDelayRspResTime OBJECT-TYPE
     SYNTAX     Unsigned32
    MAX-ACCESS read-only
     STATUS     current
     DESCRIPTION
         "The average residence time for PTP Peer Delay Response messages."
     ::= { f3PtpTrafficPortFlowPointHistoryEntry 38 }

f3PtpTrafficPortFlowPointHistoryDestMciNoMatchDiscards OBJECT-TYPE
     SYNTAX     PerfCounter64
    MAX-ACCESS read-only
     STATUS     current
     DESCRIPTION
         "The dest MCI no match discards messages."
     ::= { f3PtpTrafficPortFlowPointHistoryEntry 39 }

f3PtpTrafficPortFlowPointHistoryTagNoMatchDiscards OBJECT-TYPE
     SYNTAX     PerfCounter64
    MAX-ACCESS read-only
     STATUS     current
     DESCRIPTION
         "PTP frames discarded due to tag mismatch. For example, eth-multicast FP is tagged,
         then untagged non-forwardable PTP frames shall be discarded."
     ::= { f3PtpTrafficPortFlowPointHistoryEntry 40 }

--
-- Traffic Port PTP Flow Point Threshold Table
--
f3PtpTrafficPortFlowPointThresholdTable OBJECT-TYPE
    SYNTAX      SEQUENCE OF F3PtpTrafficPortFlowPointThresholdEntry
   MAX-ACCESS  not-accessible
    STATUS      current
    DESCRIPTION
            "A table of entries that allow manageability of Traffic Port PTP Flow Point
             Thresholds."
    ::= { f3PtpPerformanceObjects 21 }

f3PtpTrafficPortFlowPointThresholdEntry OBJECT-TYPE
    SYNTAX      F3PtpTrafficPortFlowPointThresholdEntry
   MAX-ACCESS  not-accessible
    STATUS      current
    DESCRIPTION
            "A conceptual row in the f3PtpTrafficPortFlowPointThresholdTable."
    INDEX { neIndex, shelfIndex, slotIndex, cmEthernetTrafficPortIndex, 
            f3PtpTrafficPortFlowPointIndex, f3PtpTrafficPortFlowPointStatsIndex, 
            f3PtpTrafficPortFlowPointThresholdIndex }
    ::= { f3PtpTrafficPortFlowPointThresholdTable 1 }

F3PtpTrafficPortFlowPointThresholdEntry ::= SEQUENCE {
    f3PtpTrafficPortFlowPointThresholdIndex       Integer32,
    f3PtpTrafficPortFlowPointThresholdInterval    CmPmIntervalType,
    f3PtpTrafficPortFlowPointThresholdVariable    VariablePointer,
    f3PtpTrafficPortFlowPointThresholdValueLo     Unsigned32,
    f3PtpTrafficPortFlowPointThresholdValueHi     Unsigned32,
    f3PtpTrafficPortFlowPointThresholdMonValue    PerfCounter64
}

f3PtpTrafficPortFlowPointThresholdIndex OBJECT-TYPE
    SYNTAX     Integer32 (1..65535)
   MAX-ACCESS not-accessible 
    STATUS     current
    DESCRIPTION
        "An index that uniquely identifies an entry in the
        f3PtpTrafficPortFlowPointThresholdTable."
    ::= { f3PtpTrafficPortFlowPointThresholdEntry 1 }

f3PtpTrafficPortFlowPointThresholdInterval OBJECT-TYPE
    SYNTAX     CmPmIntervalType
   MAX-ACCESS read-only
    STATUS     current
    DESCRIPTION
        "The interval over which monitored value is
        sampled and compared with the specified threshold."
    ::= { f3PtpTrafficPortFlowPointThresholdEntry 2 }

f3PtpTrafficPortFlowPointThresholdVariable OBJECT-TYPE
    SYNTAX     VariablePointer
   MAX-ACCESS read-only
    STATUS     current
    DESCRIPTION
        "The object identifier of the particular variable to be
        sampled."
    ::= { f3PtpTrafficPortFlowPointThresholdEntry 3 }

f3PtpTrafficPortFlowPointThresholdValueLo OBJECT-TYPE
    SYNTAX     Unsigned32
   MAX-ACCESS read-write
    STATUS     current
    DESCRIPTION
        "Lower 32 bits of the threshold value."
    ::= { f3PtpTrafficPortFlowPointThresholdEntry 4 }

f3PtpTrafficPortFlowPointThresholdValueHi OBJECT-TYPE
    SYNTAX     Unsigned32
   MAX-ACCESS read-write
    STATUS     current
    DESCRIPTION
        "Higher 32 bits of the threshold value."
    ::= { f3PtpTrafficPortFlowPointThresholdEntry 5 }

f3PtpTrafficPortFlowPointThresholdMonValue OBJECT-TYPE
    SYNTAX     PerfCounter64
   MAX-ACCESS read-only
    STATUS     current
    DESCRIPTION
        "Monitored value corresponding to f3PtpTrafficPortFlowPointThresholdVariable."
    ::= { f3PtpTrafficPortFlowPointThresholdEntry 6 }


--
-- PTP Clock Current Statistics Table
--
--f3PtpPTPClockStatsTable OBJECT-TYPE
--    SYNTAX      SEQUENCE OF F3PtpPTPClockStatsEntry
--    MAX-ACCESS  not-accessible
--    STATUS      current
--    DESCRIPTION
--            "A collection of PTP Clock related statistics.  
--             These reflect the current data."
--    ::= { f3PtpPerformanceObjects 22 }
--
--f3PtpPTPClockStatsEntry OBJECT-TYPE
--    SYNTAX      F3PtpPTPClockStatsEntry 
--    MAX-ACCESS  not-accessible
--    STATUS      current
--    DESCRIPTION
--            "A conceptual row in the f3PtpPTPClockStatsTable.
--             Entries exist in this table for each PTP Clock."
--    INDEX { neIndex, f3PtpPTPClockIndex,  f3PtpPTPClockStatsIndex }
--    ::= { f3PtpPTPClockStatsTable 1 }
--
--F3PtpPTPClockStatsEntry ::= SEQUENCE {
--    f3PtpPTPClockStatsIndex                Integer32,
--    f3PtpPTPClockStatsIntervalType         CmPmIntervalType,
--    f3PtpPTPClockStatsValid                TruthValue,
--    f3PtpPTPClockStatsAction               CmPmBinAction,
--    f3PtpPTPClockStatsTotalTimeCR5         Unsigned32,
--    f3PtpPTPClockStatsTotalTimeCR4         Unsigned32,
--    f3PtpPTPClockStatsTotalTimeCR3         Unsigned32,
--    f3PtpPTPClockStatsTotalTimePR5         Unsigned32,
--    f3PtpPTPClockStatsTotalTimePR4         Unsigned32,
--    f3PtpPTPClockStatsTotalTimePR3         Unsigned32
--}
--
--f3PtpPTPClockStatsIndex OBJECT-TYPE
--    SYNTAX      Integer32 (1..4)
--    MAX-ACCESS  not-accessible
--    STATUS      current
--    DESCRIPTION
--            "An arbitrary integer index value used to uniquely identify
--            this PTP Clock statistics entry. 
--            1 - 15min
--            2 - 1day
--            3 - rollover
--            4 - 5min"
--    ::= { f3PtpPTPClockStatsEntry 1 }
--
--f3PtpPTPClockStatsIntervalType OBJECT-TYPE
--    SYNTAX      CmPmIntervalType
--    MAX-ACCESS  read-only
--    STATUS      current
--    DESCRIPTION
--            "Indicates the type of collection, i.e. whether it is
--             15 Min, 1 Day or rollover."
--    ::= { f3PtpPTPClockStatsEntry 2 }
--
--f3PtpPTPClockStatsValid OBJECT-TYPE
--    SYNTAX      TruthValue
--    MAX-ACCESS  read-only
--    STATUS      current
--    DESCRIPTION
--            "Indicates the validity of the bin."
--    ::= { f3PtpPTPClockStatsEntry 3 }
--
--f3PtpPTPClockStatsAction OBJECT-TYPE
--    SYNTAX      CmPmBinAction
--    MAX-ACCESS  read-write
--    STATUS      current
--    DESCRIPTION
--            "Allows the Manager to clear the bin."
--    ::= { f3PtpPTPClockStatsEntry 4 }
--
--f3PtpPTPClockStatsTotalTimeCR5 OBJECT-TYPE
--     SYNTAX     Unsigned32
--     MAX-ACCESS read-only
--     STATUS     current
--     DESCRIPTION
--         "Total Time in seconds Clock Recovery Score is 5."
--     ::= { f3PtpPTPClockStatsEntry 5 }
--
--f3PtpPTPClockStatsTotalTimeCR4 OBJECT-TYPE
--     SYNTAX     Unsigned32
--     MAX-ACCESS read-only
--     STATUS     current
--     DESCRIPTION
--         "Total Time in seconds Clock Recovery Score is 4."
--     ::= { f3PtpPTPClockStatsEntry 6 }
--
--f3PtpPTPClockStatsTotalTimeCR3 OBJECT-TYPE
--     SYNTAX     Unsigned32
--     MAX-ACCESS read-only
--     STATUS     current
--     DESCRIPTION
--         "Total Time in seconds Clock Recovery Score is 3."
--     ::= { f3PtpPTPClockStatsEntry 7 }
--
--f3PtpPTPClockStatsTotalTimePR5 OBJECT-TYPE
--     SYNTAX     Unsigned32
--     MAX-ACCESS read-only
--     STATUS     current
--     DESCRIPTION
--         "Total Time in seconds Phase Recovery Score is 5."
--     ::= { f3PtpPTPClockStatsEntry 8 }
--
--f3PtpPTPClockStatsTotalTimePR4 OBJECT-TYPE
--     SYNTAX     Unsigned32
--     MAX-ACCESS read-only
--     STATUS     current
--     DESCRIPTION
--         "Total Time in seconds Phase Recovery Score is 4."
--     ::= { f3PtpPTPClockStatsEntry 9 }
--
--f3PtpPTPClockStatsTotalTimePR3 OBJECT-TYPE
--     SYNTAX     Unsigned32
--     MAX-ACCESS read-only
--     STATUS     current
--     DESCRIPTION
--         "Total Time in seconds Phase Recovery Score is 3."
--     ::= { f3PtpPTPClockStatsEntry 10 }
--
--
-- PTP Clock History Table
--
--f3PtpPTPClockHistoryTable OBJECT-TYPE
--    SYNTAX      SEQUENCE OF F3PtpPTPClockHistoryEntry
--    MAX-ACCESS  not-accessible
--    STATUS      current
--    DESCRIPTION
--            "A collection of PTP Clock related statistics.  
--             These reflect the historical data."
--    ::= { f3PtpPerformanceObjects 23 }
--
--f3PtpPTPClockHistoryEntry OBJECT-TYPE
--    SYNTAX      F3PtpPTPClockHistoryEntry 
--    MAX-ACCESS  not-accessible
--    STATUS      current
--    DESCRIPTION
--            "A conceptual row in the f3PtpPTPClockHistoryTable.
--             Entries exist in this table for each PTP Clock."
--    INDEX { neIndex, f3PtpPTPClockIndex,  f3PtpPTPClockStatsIndex, f3PtpPTPClockHistoryIndex }
--    ::= { f3PtpPTPClockHistoryTable 1 }
--
--F3PtpPTPClockHistoryEntry ::= SEQUENCE {
--    f3PtpPTPClockHistoryIndex                  Integer32,
--    f3PtpPTPClockHistoryTime                   DateAndTime,
--    f3PtpPTPClockHistoryValid                  TruthValue,
--    f3PtpPTPClockHistoryAction                 CmPmBinAction,
--    f3PtpPTPClockHistoryTotalTimeCR5           Unsigned32,
--    f3PtpPTPClockHistoryTotalTimeCR4           Unsigned32,
--    f3PtpPTPClockHistoryTotalTimeCR3           Unsigned32,
--    f3PtpPTPClockHistoryTotalTimePR5           Unsigned32,
--    f3PtpPTPClockHistoryTotalTimePR4           Unsigned32,
--    f3PtpPTPClockHistoryTotalTimePR3           Unsigned32
--}
--
--f3PtpPTPClockHistoryIndex OBJECT-TYPE
--    SYNTAX      Integer32 (1..32)
--    MAX-ACCESS  not-accessible
--    STATUS      current
--    DESCRIPTION
--            "An arbitrary integer index value used to uniquely identify
--            this PTP Clock statistics entry. 
--            Index 1 corresponds to 15minute, index 2 to 1 day and index
--            3 corresponds to rollover."
--    ::= { f3PtpPTPClockHistoryEntry 1 }
--
--f3PtpPTPClockHistoryTime OBJECT-TYPE
--    SYNTAX      DateAndTime 
--    MAX-ACCESS  read-only
--    STATUS      current
--    DESCRIPTION
--            "Indicates the time of history bin creation." 
--    ::= { f3PtpPTPClockHistoryEntry 2 }
--
--f3PtpPTPClockHistoryValid OBJECT-TYPE
--    SYNTAX      TruthValue
--    MAX-ACCESS  read-only
--    STATUS      current
--    DESCRIPTION
--            "Indicates the validity of the bin."
--    ::= { f3PtpPTPClockHistoryEntry 3 }
--
--f3PtpPTPClockHistoryAction OBJECT-TYPE
--    SYNTAX      CmPmBinAction
--    MAX-ACCESS  read-write
--    STATUS      current
--    DESCRIPTION
--            "Allows the Manager to clear the bin."
--    ::= { f3PtpPTPClockHistoryEntry 4 }
--
--f3PtpPTPClockHistoryTotalTimeCR5 OBJECT-TYPE
--     SYNTAX     Unsigned32
--     MAX-ACCESS read-only
--     STATUS     current
--     DESCRIPTION
--         "Total Time in seconds Clock Recovery Score is 5."
--     ::= { f3PtpPTPClockHistoryEntry 5 }
--
--f3PtpPTPClockHistoryTotalTimeCR4 OBJECT-TYPE
--     SYNTAX     Unsigned32
--     MAX-ACCESS read-only
--     STATUS     current
--     DESCRIPTION
--         "Total Time in seconds Clock Recovery Score is 4."
--     ::= { f3PtpPTPClockHistoryEntry 6 }
--
--f3PtpPTPClockHistoryTotalTimeCR3 OBJECT-TYPE
--     SYNTAX     Unsigned32
--     MAX-ACCESS read-only
--     STATUS     current
--     DESCRIPTION
--         "Total Time in seconds Clock Recovery Score is 3."
--     ::= { f3PtpPTPClockHistoryEntry 7 }
--
--f3PtpPTPClockHistoryTotalTimePR5 OBJECT-TYPE
--     SYNTAX     Unsigned32
--     MAX-ACCESS read-only
--     STATUS     current
--     DESCRIPTION
--         "Total Time in seconds Phase Recovery Score is 5."
--     ::= { f3PtpPTPClockHistoryEntry 8 }
--
--f3PtpPTPClockHistoryTotalTimePR4 OBJECT-TYPE
--     SYNTAX     Unsigned32
--     MAX-ACCESS read-only
--     STATUS     current
--     DESCRIPTION
--         "Total Time in seconds Phase Recovery Score is 4."
--     ::= { f3PtpPTPClockHistoryEntry 9 }
--
--f3PtpPTPClockHistoryTotalTimePR3 OBJECT-TYPE
--     SYNTAX     Unsigned32
--     MAX-ACCESS read-only
--     STATUS     current
--     DESCRIPTION
--         "Total Time in seconds Phase Recovery Score is 3."
--     ::= { f3PtpPTPClockHistoryEntry 10 }
--
--
--
-- PTP Clock Threshold Table
--
--f3PtpPTPClockThresholdTable OBJECT-TYPE
--    SYNTAX      SEQUENCE OF F3PtpPTPClockThresholdEntry
--    MAX-ACCESS  not-accessible
--    STATUS      current
--    DESCRIPTION
--            "A table of entries that allow manageability of 
--             PTP Clock Thresholds."
--    ::= { f3PtpPerformanceObjects 24 }
--
--f3PtpPTPClockThresholdEntry OBJECT-TYPE
--    SYNTAX      F3PtpPTPClockThresholdEntry
--    MAX-ACCESS  not-accessible
--    STATUS      current
--    DESCRIPTION
--            "A conceptual row in the f3PtpPTPClockThresholdTable."
--    INDEX { neIndex, f3PtpPTPClockIndex,  
--            f3PtpPTPClockStatsIndex, f3PtpPTPClockThresholdIndex }
--    ::= { f3PtpPTPClockThresholdTable 1 }
--
--F3PtpPTPClockThresholdEntry ::= SEQUENCE {
--    f3PtpPTPClockThresholdIndex       Integer32,
--    f3PtpPTPClockThresholdInterval    CmPmIntervalType,
--    f3PtpPTPClockThresholdVariable    VariablePointer,
--    f3PtpPTPClockThresholdValueLo     Unsigned32,
--    f3PtpPTPClockThresholdValueHi     Unsigned32,
--    f3PtpPTPClockThresholdMonValue    PerfCounter64
--}
--
--f3PtpPTPClockThresholdIndex OBJECT-TYPE
--    SYNTAX     Integer32 (1..65535)
--    MAX-ACCESS not-accessible
--    STATUS     current
--    DESCRIPTION
--        "An index that uniquely identifies an entry in the
--        f3PtpPTPClockThresholdTable."
--    ::= { f3PtpPTPClockThresholdEntry 1 }
--
--f3PtpPTPClockThresholdInterval OBJECT-TYPE
--    SYNTAX     CmPmIntervalType
--    MAX-ACCESS read-only
--    STATUS     current
--    DESCRIPTION
--        "The interval over which monitored value is
--        sampled and compared with the specified threshold."
--    ::= { f3PtpPTPClockThresholdEntry 2 }
--
--f3PtpPTPClockThresholdVariable OBJECT-TYPE
--    SYNTAX     VariablePointer
--    MAX-ACCESS read-only
--    STATUS     current
--    DESCRIPTION
--        "The object identifier of the particular variable to be
--        sampled."
--    ::= { f3PtpPTPClockThresholdEntry 3 }
--
--f3PtpPTPClockThresholdValueLo OBJECT-TYPE
--    SYNTAX     Unsigned32
--    MAX-ACCESS read-write
--    STATUS     current
--    DESCRIPTION
--        "Lower 32 bits of the threshold value."
--    ::= { f3PtpPTPClockThresholdEntry 4 }
--
--f3PtpPTPClockThresholdValueHi OBJECT-TYPE
--    SYNTAX     Unsigned32
--    MAX-ACCESS read-write
--    STATUS     current
--    DESCRIPTION
--        "Higher 32 bits of the threshold value."
--    ::= { f3PtpPTPClockThresholdEntry 5 }
--
--f3PtpPTPClockThresholdMonValue OBJECT-TYPE
--    SYNTAX     PerfCounter64
--    MAX-ACCESS read-only
--    STATUS     current
--    DESCRIPTION
--        "Monitored value corresponding to f3PtpPTPClockThresholdVariable."
--    ::= { f3PtpPTPClockThresholdEntry 6 }




--
-- PTP Port Current Statistics Table
--
f3PtpPTPPortStatsTable OBJECT-TYPE
    SYNTAX      SEQUENCE OF F3PtpPTPPortStatsEntry
    MAX-ACCESS  not-accessible
    STATUS      current
    DESCRIPTION
            "A collection of PTP Port related statistics.  
             These reflect the current data."
    ::= { f3PtpPerformanceObjects 22 }

f3PtpPTPPortStatsEntry OBJECT-TYPE
    SYNTAX      F3PtpPTPPortStatsEntry 
    MAX-ACCESS  not-accessible
    STATUS      current
    DESCRIPTION
            "A conceptual row in the f3PtpPTPPortStatsTable.
             Entries exist in this table for each PTP Port."
    INDEX { neIndex, f3PtpPTPClockIndex, f3PtpPTPPortIndex,  f3PtpPTPPortStatsIndex }
 
    ::= { f3PtpPTPPortStatsTable 1 }

F3PtpPTPPortStatsEntry ::= SEQUENCE {
    f3PtpPTPPortStatsIndex                        Integer32,
    f3PtpPTPPortStatsIntervalType                 CmPmIntervalType,
    f3PtpPTPPortStatsValid                        TruthValue,
    f3PtpPTPPortStatsAction                       CmPmBinAction,
    f3PtpPTPPortStatsAvgAnnounceRate              Unsigned32,
    f3PtpPTPPortStatsAvgSyncRate                  Unsigned32,
    f3PtpPTPPortStatsAvgDelayReqRate              Unsigned32,
    f3PtpPTPPortStatsAvgDelayRespRate             Unsigned32,
    f3PtpPTPPortStatsMismatchDomainDiscards       PerfCounter64,
    f3PtpPTPPortStatsMessageWrongTypeDiscards     PerfCounter64,
    f3PtpPTPPortStatsMessagesWrongLengthDiscards  PerfCounter64,
    f3PtpPTPPortStatsUnknownMasterDiscards        PerfCounter64,
    f3PtpPTPPortStatsMinOffsetFromMaster          PerfCounter64,
    f3PtpPTPPortStatsMaxOffsetFromMaster          PerfCounter64,
    f3PtpPTPPortStatsAvgOffsetFromMaster          PerfCounter64,
    f3PtpPTPPortStatsMinSyncPathDelay             PerfCounter64,
    f3PtpPTPPortStatsMaxSyncPathDelay             PerfCounter64,
    f3PtpPTPPortStatsAvgSyncPathDelay             PerfCounter64,
    f3PtpPTPPortStatsMinMeanPathDelay             PerfCounter64,
    f3PtpPTPPortStatsMaxMeanPathDelay             PerfCounter64,
    f3PtpPTPPortStatsAvgMeanPathDelay             PerfCounter64,
    f3PtpPTPPortStatsMsgMiscDiscards              PerfCounter64,
    f3PtpPTPPortStatsAvgLinkDelay                 Unsigned32,
    f3PtpPTPPortStatsMinLinkDelay                 Unsigned32,
    f3PtpPTPPortStatsMaxLinkDelay                 Unsigned32
}

f3PtpPTPPortStatsIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPPortStatsEntry 1 }

f3PtpPTPPortStatsIntervalType OBJECT-TYPE
    SYNTAX      CmPmIntervalType
    MAX-ACCESS  read-only
    STATUS      current
    DESCRIPTION
            "Indicates the type of collection, i.e. whether it is
             15 Min, 1 Day or rollover."
    ::= { f3PtpPTPPortStatsEntry 2 }

f3PtpPTPPortStatsValid OBJECT-TYPE
    SYNTAX      TruthValue
    MAX-ACCESS  read-only
    STATUS      current
    DESCRIPTION
            "Indicates the validity of the bin."
    ::= { f3PtpPTPPortStatsEntry 3 }

f3PtpPTPPortStatsAction OBJECT-TYPE
    SYNTAX      CmPmBinAction
    MAX-ACCESS  read-write
    STATUS      current
    DESCRIPTION
            "Allows the Manager to clear the bin."
    ::= { f3PtpPTPPortStatsEntry 4 }

f3PtpPTPPortStatsAvgAnnounceRate OBJECT-TYPE
     SYNTAX     Unsigned32
     MAX-ACCESS read-only
     STATUS     current
     DESCRIPTION
         "Avg Announce Rate."
     ::= { f3PtpPTPPortStatsEntry 5 }

f3PtpPTPPortStatsAvgSyncRate OBJECT-TYPE
     SYNTAX     Unsigned32
     MAX-ACCESS read-only
     STATUS     current
     DESCRIPTION
         "Avg Sync Rate."
     ::= { f3PtpPTPPortStatsEntry 6 }

f3PtpPTPPortStatsAvgDelayReqRate OBJECT-TYPE
     SYNTAX     Unsigned32
     MAX-ACCESS read-only
     STATUS     current
     DESCRIPTION
         "Avg Delay Req Rate."
     ::= { f3PtpPTPPortStatsEntry 7 }

f3PtpPTPPortStatsAvgDelayRespRate OBJECT-TYPE
     SYNTAX     Unsigned32
     MAX-ACCESS read-only
     STATUS     current
     DESCRIPTION
         "Avg Delay Resp Rate."
     ::= { f3PtpPTPPortStatsEntry 8 }

f3PtpPTPPortStatsMismatchDomainDiscards OBJECT-TYPE
     SYNTAX     PerfCounter64
     MAX-ACCESS read-only
     STATUS     current
     DESCRIPTION
         "Mismatch Domain Discards."
     ::= { f3PtpPTPPortStatsEntry 9 }

f3PtpPTPPortStatsMessageWrongTypeDiscards OBJECT-TYPE
     SYNTAX     PerfCounter64
     MAX-ACCESS read-only
     STATUS     current
     DESCRIPTION
         "Message Wrong Type Discards."
     ::= { f3PtpPTPPortStatsEntry 10 }

f3PtpPTPPortStatsMessagesWrongLengthDiscards OBJECT-TYPE
     SYNTAX     PerfCounter64
     MAX-ACCESS read-only
     STATUS     current
     DESCRIPTION
         "Messages Wrong Length Discards."
     ::= { f3PtpPTPPortStatsEntry 11 }

f3PtpPTPPortStatsUnknownMasterDiscards OBJECT-TYPE
     SYNTAX     PerfCounter64
     MAX-ACCESS read-only
     STATUS     deprecated
     DESCRIPTION
         "Unknown Master Discards."
     ::= { f3PtpPTPPortStatsEntry 12 }

f3PtpPTPPortStatsMinOffsetFromMaster OBJECT-TYPE
     SYNTAX     PerfCounter64
     MAX-ACCESS read-only
     STATUS     current
     DESCRIPTION
         "Min Offset From Master."
     ::= { f3PtpPTPPortStatsEntry 13 }

f3PtpPTPPortStatsMaxOffsetFromMaster OBJECT-TYPE
     SYNTAX     PerfCounter64
     MAX-ACCESS read-only
     STATUS     current
     DESCRIPTION
         "Max Offset From Master."
     ::= { f3PtpPTPPortStatsEntry 14 }

f3PtpPTPPortStatsAvgOffsetFromMaster OBJECT-TYPE
     SYNTAX     PerfCounter64
     MAX-ACCESS read-only
     STATUS     current
     DESCRIPTION
         "Avg Offset From Master."
     ::= { f3PtpPTPPortStatsEntry 15 }

f3PtpPTPPortStatsMinSyncPathDelay OBJECT-TYPE
     SYNTAX     PerfCounter64
     MAX-ACCESS read-only
     STATUS     current
     DESCRIPTION
         "Min Sync Path Delay."
     ::= { f3PtpPTPPortStatsEntry 16 }

f3PtpPTPPortStatsMaxSyncPathDelay OBJECT-TYPE
     SYNTAX     PerfCounter64
     MAX-ACCESS read-only
     STATUS     current
     DESCRIPTION
         "Max Sync Path Delay."
     ::= { f3PtpPTPPortStatsEntry 17 }

f3PtpPTPPortStatsAvgSyncPathDelay OBJECT-TYPE
     SYNTAX     PerfCounter64
     MAX-ACCESS read-only
     STATUS     current
     DESCRIPTION
         "Avg Sync Path Delay."
     ::= { f3PtpPTPPortStatsEntry 18 }


f3PtpPTPPortStatsMinMeanPathDelay OBJECT-TYPE
     SYNTAX     PerfCounter64
     MAX-ACCESS read-only
     STATUS     current
     DESCRIPTION
         "Min Mean Path Delay."
     ::= { f3PtpPTPPortStatsEntry 19 }

f3PtpPTPPortStatsMaxMeanPathDelay OBJECT-TYPE
     SYNTAX     PerfCounter64
     MAX-ACCESS read-only
     STATUS     current
     DESCRIPTION
         "Max Mean Path Delay."
     ::= { f3PtpPTPPortStatsEntry 20 }

f3PtpPTPPortStatsAvgMeanPathDelay OBJECT-TYPE
     SYNTAX     PerfCounter64
     MAX-ACCESS read-only
     STATUS     current
     DESCRIPTION
         "Avg Mean Path Delay."
     ::= { f3PtpPTPPortStatsEntry 21 }

f3PtpPTPPortStatsMsgMiscDiscards OBJECT-TYPE
     SYNTAX     PerfCounter64
     MAX-ACCESS read-only
     STATUS     deprecated
     DESCRIPTION
         "Number of received packets discarded due to miscellaneous reasons."
     ::= { f3PtpPTPPortStatsEntry 22 }


f3PtpPTPPortStatsAvgLinkDelay OBJECT-TYPE
     SYNTAX     Unsigned32
     MAX-ACCESS read-only
     STATUS     current
     DESCRIPTION
         "Avg Link Delay."
     ::= { f3PtpPTPPortStatsEntry 23 }

f3PtpPTPPortStatsMinLinkDelay OBJECT-TYPE
     SYNTAX     Unsigned32
     MAX-ACCESS read-only
     STATUS     current
     DESCRIPTION
         "Min Link Delay."
     ::= { f3PtpPTPPortStatsEntry 24 }

f3PtpPTPPortStatsMaxLinkDelay OBJECT-TYPE
     SYNTAX     Unsigned32
     MAX-ACCESS read-only
     STATUS     current
     DESCRIPTION
         "Max Link Delay."
     ::= { f3PtpPTPPortStatsEntry 25 }



--
-- PTP Port Current History Table
--
f3PtpPTPPortHistoryTable OBJECT-TYPE
    SYNTAX      SEQUENCE OF F3PtpPTPPortHistoryEntry
    MAX-ACCESS  not-accessible
    STATUS      current
    DESCRIPTION
            "A collection of PTP Port related statistics.  
             These reflect the current data."
    ::= { f3PtpPerformanceObjects 23 }

f3PtpPTPPortHistoryEntry OBJECT-TYPE
    SYNTAX      F3PtpPTPPortHistoryEntry 
    MAX-ACCESS  not-accessible
    STATUS      current
    DESCRIPTION
            "A conceptual row in the f3PtpPTPPortHistoryTable.
             Entries exist in this table for each PTP Port."
    INDEX { neIndex, f3PtpPTPClockIndex, f3PtpPTPPortIndex,  f3PtpPTPPortStatsIndex, f3PtpPTPPortHistoryIndex }

    ::= { f3PtpPTPPortHistoryTable 1 }

F3PtpPTPPortHistoryEntry ::= SEQUENCE {
    f3PtpPTPPortHistoryIndex                        Integer32,
    f3PtpPTPPortHistoryTime                         DateAndTime,
    f3PtpPTPPortHistoryValid                        TruthValue,
    f3PtpPTPPortHistoryAction                       CmPmBinAction,
    f3PtpPTPPortHistoryAvgAnnounceRate              Unsigned32,
    f3PtpPTPPortHistoryAvgSyncRate                  Unsigned32,
    f3PtpPTPPortHistoryAvgDelayReqRate              Unsigned32,
    f3PtpPTPPortHistoryAvgDelayRespRate             Unsigned32,
    f3PtpPTPPortHistoryMismatchDomainDiscards       PerfCounter64,
    f3PtpPTPPortHistoryMessageWrongTypeDiscards     PerfCounter64,
    f3PtpPTPPortHistoryMessagesWrongLengthDiscards  PerfCounter64,
    f3PtpPTPPortHistoryUnknownMasterDiscards        PerfCounter64,
    f3PtpPTPPortHistoryMinOffsetFromMaster          PerfCounter64,
    f3PtpPTPPortHistoryMaxOffsetFromMaster          PerfCounter64,
    f3PtpPTPPortHistoryAvgOffsetFromMaster          PerfCounter64,
    f3PtpPTPPortHistoryMinSyncPathDelay             PerfCounter64,
    f3PtpPTPPortHistoryMaxSyncPathDelay             PerfCounter64,
    f3PtpPTPPortHistoryAvgSyncPathDelay             PerfCounter64,
    f3PtpPTPPortHistoryMinMeanPathDelay             PerfCounter64,
    f3PtpPTPPortHistoryMaxMeanPathDelay             PerfCounter64,
    f3PtpPTPPortHistoryAvgMeanPathDelay             PerfCounter64,
    f3PtpPTPPortHistoryMsgMiscDiscards              PerfCounter64,
    f3PtpPTPPortHistoryAvgLinkDelay                 Unsigned32,
    f3PtpPTPPortHistoryMinLinkDelay                 Unsigned32,
    f3PtpPTPPortHistoryMaxLinkDelay                 Unsigned32
}

f3PtpPTPPortHistoryIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPPortHistoryEntry 1 }

f3PtpPTPPortHistoryTime OBJECT-TYPE
    SYNTAX      DateAndTime
    MAX-ACCESS  read-only
    STATUS      current
    DESCRIPTION
            "Indicates the time of history bin creation." 
    ::= { f3PtpPTPPortHistoryEntry 2 }

f3PtpPTPPortHistoryValid OBJECT-TYPE
    SYNTAX      TruthValue
    MAX-ACCESS  read-only
    STATUS      current
    DESCRIPTION
            "Indicates the validity of the bin."
    ::= { f3PtpPTPPortHistoryEntry 3 }

f3PtpPTPPortHistoryAction OBJECT-TYPE
    SYNTAX      CmPmBinAction
    MAX-ACCESS  read-write
    STATUS      current
    DESCRIPTION
            "Allows the Manager to clear the bin."
    ::= { f3PtpPTPPortHistoryEntry 4 }

f3PtpPTPPortHistoryAvgAnnounceRate OBJECT-TYPE
     SYNTAX     Unsigned32
     MAX-ACCESS read-only
     STATUS     current
     DESCRIPTION
         "Avg Announce Rate."
     ::= { f3PtpPTPPortHistoryEntry 5 }

f3PtpPTPPortHistoryAvgSyncRate OBJECT-TYPE
     SYNTAX     Unsigned32
     MAX-ACCESS read-only
     STATUS     current
     DESCRIPTION
         "Avg Sync Rate."
     ::= { f3PtpPTPPortHistoryEntry 6 }

f3PtpPTPPortHistoryAvgDelayReqRate OBJECT-TYPE
     SYNTAX     Unsigned32
     MAX-ACCESS read-only
     STATUS     current
     DESCRIPTION
         "Avg Delay Req Rate."
     ::= { f3PtpPTPPortHistoryEntry 7 }

f3PtpPTPPortHistoryAvgDelayRespRate OBJECT-TYPE
     SYNTAX     Unsigned32
     MAX-ACCESS read-only
     STATUS     current
     DESCRIPTION
         "Avg Delay Resp Rate."
     ::= { f3PtpPTPPortHistoryEntry 8 }

f3PtpPTPPortHistoryMismatchDomainDiscards OBJECT-TYPE
     SYNTAX     PerfCounter64
     MAX-ACCESS read-only
     STATUS     current
     DESCRIPTION
         "Mismatch Domain Discards."
     ::= { f3PtpPTPPortHistoryEntry 9 }

f3PtpPTPPortHistoryMessageWrongTypeDiscards OBJECT-TYPE
     SYNTAX     PerfCounter64
     MAX-ACCESS read-only
     STATUS     current
     DESCRIPTION
         "Message Wrong Type Discards."
     ::= { f3PtpPTPPortHistoryEntry 10 }

f3PtpPTPPortHistoryMessagesWrongLengthDiscards OBJECT-TYPE
     SYNTAX     PerfCounter64
     MAX-ACCESS read-only
     STATUS     current
     DESCRIPTION
         "Messages Wrong Length Discards."
     ::= { f3PtpPTPPortHistoryEntry 11 }

f3PtpPTPPortHistoryUnknownMasterDiscards OBJECT-TYPE
     SYNTAX     PerfCounter64
     MAX-ACCESS read-only
     STATUS     deprecated
     DESCRIPTION
         "Unknown Master Discards."
     ::= { f3PtpPTPPortHistoryEntry 12 }

f3PtpPTPPortHistoryMinOffsetFromMaster OBJECT-TYPE
     SYNTAX     PerfCounter64
     MAX-ACCESS read-only
     STATUS     current
     DESCRIPTION
         "Min Offset From Master."
     ::= { f3PtpPTPPortHistoryEntry 13 }

f3PtpPTPPortHistoryMaxOffsetFromMaster OBJECT-TYPE
     SYNTAX     PerfCounter64
     MAX-ACCESS read-only
     STATUS     current
     DESCRIPTION
         "Max Offset From Master."
     ::= { f3PtpPTPPortHistoryEntry 14 }

f3PtpPTPPortHistoryAvgOffsetFromMaster OBJECT-TYPE
     SYNTAX     PerfCounter64
     MAX-ACCESS read-only
     STATUS     current
     DESCRIPTION
         "Avg Offset From Master."
     ::= { f3PtpPTPPortHistoryEntry 15 }

f3PtpPTPPortHistoryMinSyncPathDelay OBJECT-TYPE
     SYNTAX     PerfCounter64
     MAX-ACCESS read-only
     STATUS     current
     DESCRIPTION
         "Min Sync Path Delay."
     ::= { f3PtpPTPPortHistoryEntry 16 }

f3PtpPTPPortHistoryMaxSyncPathDelay OBJECT-TYPE
     SYNTAX     PerfCounter64
     MAX-ACCESS read-only
     STATUS     current
     DESCRIPTION
         "Max Sync Path Delay."
     ::= { f3PtpPTPPortHistoryEntry 17 }

f3PtpPTPPortHistoryAvgSyncPathDelay OBJECT-TYPE
     SYNTAX     PerfCounter64
     MAX-ACCESS read-only
     STATUS     current
     DESCRIPTION
         "Avg Sync Path Delay."
     ::= { f3PtpPTPPortHistoryEntry 18 }

f3PtpPTPPortHistoryMinMeanPathDelay OBJECT-TYPE
     SYNTAX     PerfCounter64
     MAX-ACCESS read-only
     STATUS     current
     DESCRIPTION
         "Min Mean Path Delay."
     ::= { f3PtpPTPPortHistoryEntry 19 }

f3PtpPTPPortHistoryMaxMeanPathDelay OBJECT-TYPE
     SYNTAX     PerfCounter64
     MAX-ACCESS read-only
     STATUS     current
     DESCRIPTION
         "Max Mean Path Delay."
     ::= { f3PtpPTPPortHistoryEntry 20 }

f3PtpPTPPortHistoryAvgMeanPathDelay OBJECT-TYPE
     SYNTAX     PerfCounter64
     MAX-ACCESS read-only
     STATUS     current
     DESCRIPTION
         "Avg Mean Path Delay."
     ::= { f3PtpPTPPortHistoryEntry 21 }

f3PtpPTPPortHistoryMsgMiscDiscards OBJECT-TYPE
     SYNTAX     PerfCounter64
     MAX-ACCESS read-only
     STATUS     deprecated
     DESCRIPTION
         "Number of received packets discarded due to miscellaneous reasons."
     ::= { f3PtpPTPPortHistoryEntry 22 }


f3PtpPTPPortHistoryAvgLinkDelay OBJECT-TYPE
     SYNTAX     Unsigned32
     MAX-ACCESS read-only
     STATUS     current
     DESCRIPTION
         "Avg Link Delay."
     ::= { f3PtpPTPPortHistoryEntry 23 }

f3PtpPTPPortHistoryMinLinkDelay OBJECT-TYPE
     SYNTAX     Unsigned32
     MAX-ACCESS read-only
     STATUS     current
     DESCRIPTION
         "Min Link Delay."
     ::= { f3PtpPTPPortHistoryEntry 24 }

f3PtpPTPPortHistoryMaxLinkDelay OBJECT-TYPE
     SYNTAX     Unsigned32
     MAX-ACCESS read-only
     STATUS     current
     DESCRIPTION
         "Max Link Delay."
     ::= { f3PtpPTPPortHistoryEntry 25 }



--
-- PTP Port Threshold Table
--
f3PtpPTPPortThresholdTable OBJECT-TYPE
    SYNTAX      SEQUENCE OF F3PtpPTPPortThresholdEntry
    MAX-ACCESS  not-accessible
    STATUS      current
    DESCRIPTION
            "A table of entries that allow manageability of 
             PTP Port Thresholds."
    ::= { f3PtpPerformanceObjects 24 }

f3PtpPTPPortThresholdEntry OBJECT-TYPE
    SYNTAX      F3PtpPTPPortThresholdEntry
    MAX-ACCESS  not-accessible
    STATUS      current
    DESCRIPTION
            "A conceptual row in the f3PtpPTPPortThresholdTable."
    INDEX { neIndex, f3PtpPTPClockIndex, f3PtpPTPPortIndex,  
            f3PtpPTPPortStatsIndex, f3PtpPTPPortThresholdIndex }
    ::= { f3PtpPTPPortThresholdTable 1 }

F3PtpPTPPortThresholdEntry ::= SEQUENCE {
    f3PtpPTPPortThresholdIndex       Integer32,
    f3PtpPTPPortThresholdInterval    CmPmIntervalType,
    f3PtpPTPPortThresholdVariable    VariablePointer,
    f3PtpPTPPortThresholdValueLo     Unsigned32,
    f3PtpPTPPortThresholdValueHi     Unsigned32,
    f3PtpPTPPortThresholdMonValue    PerfCounter64
}

f3PtpPTPPortThresholdIndex OBJECT-TYPE
    SYNTAX     Integer32 (1..65535)
    MAX-ACCESS not-accessible
    STATUS     current
    DESCRIPTION
        "An index that uniquely identifies an entry in the
        f3PtpPTPPortThresholdTable."
    ::= { f3PtpPTPPortThresholdEntry 1 }

f3PtpPTPPortThresholdInterval OBJECT-TYPE
    SYNTAX     CmPmIntervalType
    MAX-ACCESS read-only
    STATUS     current
    DESCRIPTION
        "The interval over which monitored value is
        sampled and compared with the specified threshold."
    ::= { f3PtpPTPPortThresholdEntry 2 }

f3PtpPTPPortThresholdVariable OBJECT-TYPE
    SYNTAX     VariablePointer
    MAX-ACCESS read-only
    STATUS     current
    DESCRIPTION
        "The object identifier of the particular variable to be
        sampled."
    ::= { f3PtpPTPPortThresholdEntry 3 }

f3PtpPTPPortThresholdValueLo OBJECT-TYPE
    SYNTAX     Unsigned32
    MAX-ACCESS read-write
    STATUS     current
    DESCRIPTION
        "Lower 32 bits of the threshold value."
    ::= { f3PtpPTPPortThresholdEntry 4 }

f3PtpPTPPortThresholdValueHi OBJECT-TYPE
    SYNTAX     Unsigned32
    MAX-ACCESS read-write
    STATUS     current
    DESCRIPTION
        "Higher 32 bits of the threshold value."
    ::= { f3PtpPTPPortThresholdEntry 5 }

f3PtpPTPPortThresholdMonValue OBJECT-TYPE
    SYNTAX     PerfCounter64
    MAX-ACCESS read-only
    STATUS     current
    DESCRIPTION
        "Monitored value corresponding to f3PtpPTPPortThresholdVariable."
    ::= { f3PtpPTPPortThresholdEntry 6 }


--
-- PTP Clock Current Statistics Table
--
f3PtpPTPClockStatsTable OBJECT-TYPE
    SYNTAX      SEQUENCE OF F3PtpPTPClockStatsEntry
    MAX-ACCESS  not-accessible
    STATUS      current
    DESCRIPTION
            "A collection of PTP Clock related statistics.  
             These reflect the current data."
    ::= { f3PtpPerformanceObjects 25 }

f3PtpPTPClockStatsEntry OBJECT-TYPE
    SYNTAX      F3PtpPTPClockStatsEntry 
    MAX-ACCESS  not-accessible
    STATUS      current
    DESCRIPTION
            "A conceptual row in the f3PtpPTPClockStatsTable.
             Entries exist in this table for each PTP Port."
    INDEX { neIndex, f3PtpPTPClockIndex, f3PtpPTPClockStatsIndex }
 
    ::= { f3PtpPTPClockStatsTable 1 }

F3PtpPTPClockStatsEntry ::= SEQUENCE {
    f3PtpPTPClockStatsIndex                        Integer32,
    f3PtpPTPClockStatsIntervalType                 CmPmIntervalType,
    f3PtpPTPClockStatsValid                        TruthValue,
    f3PtpPTPClockStatsAction                       CmPmBinAction,
    f3PtpPTPClockStatsMinOffsetFromMaster          ScaledNanoseconds,
    f3PtpPTPClockStatsMaxOffsetFromMaster          ScaledNanoseconds,
    f3PtpPTPClockStatsAvgOffsetFromMaster          ScaledNanoseconds,
    f3PtpPTPClockStatsMinSyncPathDelay             ScaledNanoseconds,
    f3PtpPTPClockStatsMaxSyncPathDelay             ScaledNanoseconds,
    f3PtpPTPClockStatsAvgSyncPathDelay             ScaledNanoseconds,
    f3PtpPTPClockStatsMinMeanPathDelay             ScaledNanoseconds,
    f3PtpPTPClockStatsMaxMeanPathDelay             ScaledNanoseconds,
    f3PtpPTPClockStatsAvgMeanPathDelay             ScaledNanoseconds
}

f3PtpPTPClockStatsIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPClockStatsEntry 1 }

f3PtpPTPClockStatsIntervalType OBJECT-TYPE
    SYNTAX      CmPmIntervalType
    MAX-ACCESS  read-only
    STATUS      current
    DESCRIPTION
            "Indicates the type of collection, i.e. whether it is
             15 Min, 1 Day or rollover."
    ::= { f3PtpPTPClockStatsEntry 2 }

f3PtpPTPClockStatsValid OBJECT-TYPE
    SYNTAX      TruthValue
    MAX-ACCESS  read-only
    STATUS      current
    DESCRIPTION
            "Indicates the validity of the bin."
    ::= { f3PtpPTPClockStatsEntry 3 }

f3PtpPTPClockStatsAction OBJECT-TYPE
    SYNTAX      CmPmBinAction
    MAX-ACCESS  read-write
    STATUS      current
    DESCRIPTION
            "Allows the Manager to clear the bin."
    ::= { f3PtpPTPClockStatsEntry 4 }

f3PtpPTPClockStatsMinOffsetFromMaster OBJECT-TYPE
     SYNTAX     ScaledNanoseconds
     MAX-ACCESS read-only
     STATUS     current
     DESCRIPTION
         "Min Offset From Master."
     ::= { f3PtpPTPClockStatsEntry 5 }

f3PtpPTPClockStatsMaxOffsetFromMaster OBJECT-TYPE
     SYNTAX     ScaledNanoseconds
     MAX-ACCESS read-only
     STATUS     current
     DESCRIPTION
         "Max Offset From Master."
     ::= { f3PtpPTPClockStatsEntry 6 }

f3PtpPTPClockStatsAvgOffsetFromMaster OBJECT-TYPE
     SYNTAX     ScaledNanoseconds
     MAX-ACCESS read-only
     STATUS     current
     DESCRIPTION
         "Avg Offset From Master."
     ::= { f3PtpPTPClockStatsEntry 7 }

f3PtpPTPClockStatsMinSyncPathDelay OBJECT-TYPE
     SYNTAX     ScaledNanoseconds
     MAX-ACCESS read-only
     STATUS     current
     DESCRIPTION
         "Min Sync Path Delay."
     ::= { f3PtpPTPClockStatsEntry 8 }

f3PtpPTPClockStatsMaxSyncPathDelay OBJECT-TYPE
     SYNTAX     ScaledNanoseconds
     MAX-ACCESS read-only
     STATUS     current
     DESCRIPTION
         "Max Sync Path Delay."
     ::= { f3PtpPTPClockStatsEntry 9 }

f3PtpPTPClockStatsAvgSyncPathDelay OBJECT-TYPE
     SYNTAX     ScaledNanoseconds
     MAX-ACCESS read-only
     STATUS     current
     DESCRIPTION
         "Avg Sync Path Delay."
     ::= { f3PtpPTPClockStatsEntry 10 }


f3PtpPTPClockStatsMinMeanPathDelay OBJECT-TYPE
     SYNTAX     ScaledNanoseconds
     MAX-ACCESS read-only
     STATUS     current
     DESCRIPTION
         "Min Mean Path Delay."
     ::= { f3PtpPTPClockStatsEntry 11 }

f3PtpPTPClockStatsMaxMeanPathDelay OBJECT-TYPE
     SYNTAX     ScaledNanoseconds
     MAX-ACCESS read-only
     STATUS     current
     DESCRIPTION
         "Max Mean Path Delay."
     ::= { f3PtpPTPClockStatsEntry 12 }

f3PtpPTPClockStatsAvgMeanPathDelay OBJECT-TYPE
     SYNTAX     ScaledNanoseconds
     MAX-ACCESS read-only
     STATUS     current
     DESCRIPTION
         "Avg Mean Path Delay."
     ::= { f3PtpPTPClockStatsEntry 13 }

--
-- PTP Clock Current History Table
--
f3PtpPTPClockHistoryTable OBJECT-TYPE
    SYNTAX      SEQUENCE OF F3PtpPTPClockHistoryEntry
    MAX-ACCESS  not-accessible
    STATUS      current
    DESCRIPTION
            "A collection of PTP Clock related statistics.  
             These reflect the current data."
    ::= { f3PtpPerformanceObjects 26 }

f3PtpPTPClockHistoryEntry OBJECT-TYPE
    SYNTAX      F3PtpPTPClockHistoryEntry 
    MAX-ACCESS  not-accessible
    STATUS      current
    DESCRIPTION
            "A conceptual row in the f3PtpPTPClockHistoryTable.
             Entries exist in this table for each PTP Port."
    INDEX { neIndex, f3PtpPTPClockIndex, f3PtpPTPClockStatsIndex, f3PtpPTPClockHistoryIndex }

    ::= { f3PtpPTPClockHistoryTable 1 }

F3PtpPTPClockHistoryEntry ::= SEQUENCE {
    f3PtpPTPClockHistoryIndex                        Integer32,
    f3PtpPTPClockHistoryTime                         DateAndTime,
    f3PtpPTPClockHistoryValid                        TruthValue,
    f3PtpPTPClockHistoryAction                       CmPmBinAction,
    f3PtpPTPClockHistoryMinOffsetFromMaster          ScaledNanoseconds,
    f3PtpPTPClockHistoryMaxOffsetFromMaster          ScaledNanoseconds,
    f3PtpPTPClockHistoryAvgOffsetFromMaster          ScaledNanoseconds,
    f3PtpPTPClockHistoryMinSyncPathDelay             ScaledNanoseconds,
    f3PtpPTPClockHistoryMaxSyncPathDelay             ScaledNanoseconds,
    f3PtpPTPClockHistoryAvgSyncPathDelay             ScaledNanoseconds,
    f3PtpPTPClockHistoryMinMeanPathDelay             ScaledNanoseconds,
    f3PtpPTPClockHistoryMaxMeanPathDelay             ScaledNanoseconds,
    f3PtpPTPClockHistoryAvgMeanPathDelay             ScaledNanoseconds
}

f3PtpPTPClockHistoryIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPClockHistoryEntry 1 }

f3PtpPTPClockHistoryTime OBJECT-TYPE
    SYNTAX      DateAndTime
    MAX-ACCESS  read-only
    STATUS      current
    DESCRIPTION
            "Indicates the time of history bin creation." 
    ::= { f3PtpPTPClockHistoryEntry 2 }

f3PtpPTPClockHistoryValid OBJECT-TYPE
    SYNTAX      TruthValue
    MAX-ACCESS  read-only
    STATUS      current
    DESCRIPTION
            "Indicates the validity of the bin."
    ::= { f3PtpPTPClockHistoryEntry 3 }

f3PtpPTPClockHistoryAction OBJECT-TYPE
    SYNTAX      CmPmBinAction
    MAX-ACCESS  read-write
    STATUS      current
    DESCRIPTION
            "Allows the Manager to clear the bin."
    ::= { f3PtpPTPClockHistoryEntry 4 }

f3PtpPTPClockHistoryMinOffsetFromMaster OBJECT-TYPE
     SYNTAX     ScaledNanoseconds
     MAX-ACCESS read-only
     STATUS     current
     DESCRIPTION
         "Min Offset From Master."
     ::= { f3PtpPTPClockHistoryEntry 5 }

f3PtpPTPClockHistoryMaxOffsetFromMaster OBJECT-TYPE
     SYNTAX     ScaledNanoseconds
     MAX-ACCESS read-only
     STATUS     current
     DESCRIPTION
         "Max Offset From Master."
     ::= { f3PtpPTPClockHistoryEntry 6 }

f3PtpPTPClockHistoryAvgOffsetFromMaster OBJECT-TYPE
     SYNTAX     ScaledNanoseconds
     MAX-ACCESS read-only
     STATUS     current
     DESCRIPTION
         "Avg Offset From Master."
     ::= { f3PtpPTPClockHistoryEntry 7 }

f3PtpPTPClockHistoryMinSyncPathDelay OBJECT-TYPE
     SYNTAX     ScaledNanoseconds
     MAX-ACCESS read-only
     STATUS     current
     DESCRIPTION
         "Min Sync Path Delay."
     ::= { f3PtpPTPClockHistoryEntry 8 }

f3PtpPTPClockHistoryMaxSyncPathDelay OBJECT-TYPE
     SYNTAX     ScaledNanoseconds
     MAX-ACCESS read-only
     STATUS     current
     DESCRIPTION
         "Max Sync Path Delay."
     ::= { f3PtpPTPClockHistoryEntry 9 }

f3PtpPTPClockHistoryAvgSyncPathDelay OBJECT-TYPE
     SYNTAX     ScaledNanoseconds
     MAX-ACCESS read-only
     STATUS     current
     DESCRIPTION
         "Avg Sync Path Delay."
     ::= { f3PtpPTPClockHistoryEntry 10 }

f3PtpPTPClockHistoryMinMeanPathDelay OBJECT-TYPE
     SYNTAX     ScaledNanoseconds
     MAX-ACCESS read-only
     STATUS     current
     DESCRIPTION
         "Min Mean Path Delay."
     ::= { f3PtpPTPClockHistoryEntry 11 }

f3PtpPTPClockHistoryMaxMeanPathDelay OBJECT-TYPE
     SYNTAX     ScaledNanoseconds
     MAX-ACCESS read-only
     STATUS     current
     DESCRIPTION
         "Max Mean Path Delay."
     ::= { f3PtpPTPClockHistoryEntry 12 }

f3PtpPTPClockHistoryAvgMeanPathDelay OBJECT-TYPE
     SYNTAX     ScaledNanoseconds
     MAX-ACCESS read-only
     STATUS     current
     DESCRIPTION
         "Avg Mean Path Delay."
     ::= { f3PtpPTPClockHistoryEntry 13 }



--
-- PTP Clock Threshold Table
--
f3PtpPTPClockThresholdTable OBJECT-TYPE
    SYNTAX      SEQUENCE OF F3PtpPTPClockThresholdEntry
    MAX-ACCESS  not-accessible
    STATUS      current
    DESCRIPTION
            "A table of entries that allow manageability of 
             PTP Clock Thresholds."
    ::= { f3PtpPerformanceObjects 27 }

f3PtpPTPClockThresholdEntry OBJECT-TYPE
    SYNTAX      F3PtpPTPClockThresholdEntry
    MAX-ACCESS  not-accessible
    STATUS      current
    DESCRIPTION
            "A conceptual row in the f3PtpPTPClockThresholdTable."
    INDEX { neIndex, f3PtpPTPClockIndex,  
            f3PtpPTPClockStatsIndex, f3PtpPTPClockThresholdIndex }
    ::= { f3PtpPTPClockThresholdTable 1 }

F3PtpPTPClockThresholdEntry ::= SEQUENCE {
    f3PtpPTPClockThresholdIndex       Integer32,
    f3PtpPTPClockThresholdInterval    CmPmIntervalType,
    f3PtpPTPClockThresholdVariable    VariablePointer,
    f3PtpPTPClockThresholdValueLo     Unsigned32,
    f3PtpPTPClockThresholdValueHi     Unsigned32,
    f3PtpPTPClockThresholdMonValue    PerfCounter64
}

f3PtpPTPClockThresholdIndex OBJECT-TYPE
    SYNTAX     Integer32 (1..65535)
    MAX-ACCESS not-accessible
    STATUS     current
    DESCRIPTION
        "An index that uniquely identifies an entry in the
        f3PtpPTPClockThresholdTable."
    ::= { f3PtpPTPClockThresholdEntry 1 }

f3PtpPTPClockThresholdInterval OBJECT-TYPE
    SYNTAX     CmPmIntervalType
    MAX-ACCESS read-only
    STATUS     current
    DESCRIPTION
        "The interval over which monitored value is
        sampled and compared with the specified threshold."
    ::= { f3PtpPTPClockThresholdEntry 2 }

f3PtpPTPClockThresholdVariable OBJECT-TYPE
    SYNTAX     VariablePointer
    MAX-ACCESS read-only
    STATUS     current
    DESCRIPTION
        "The object identifier of the particular variable to be
        sampled."
    ::= { f3PtpPTPClockThresholdEntry 3 }

f3PtpPTPClockThresholdValueLo OBJECT-TYPE
    SYNTAX     Unsigned32
    MAX-ACCESS read-write
    STATUS     current
    DESCRIPTION
        "Lower 32 bits of the threshold value."
    ::= { f3PtpPTPClockThresholdEntry 4 }

f3PtpPTPClockThresholdValueHi OBJECT-TYPE
    SYNTAX     Unsigned32
    MAX-ACCESS read-write
    STATUS     current
    DESCRIPTION
        "Higher 32 bits of the threshold value."
    ::= { f3PtpPTPClockThresholdEntry 5 }

f3PtpPTPClockThresholdMonValue OBJECT-TYPE
    SYNTAX     PerfCounter64
    MAX-ACCESS read-only
    STATUS     current
    DESCRIPTION
        "Monitored value corresponding to f3PtpPTPClockThresholdVariable."
    ::= { f3PtpPTPClockThresholdEntry 6 }

--
-- L3 PTP Port Current Statistics Table
--
f3PtpL3PTPPortStatsTable OBJECT-TYPE
    SYNTAX      SEQUENCE OF F3PtpL3PTPPortStatsEntry
    MAX-ACCESS  not-accessible
    STATUS      current
    DESCRIPTION
            "A collection of PTP Port related statistics.  
             These reflect the current data."
    ::= { f3PtpPerformanceObjects 28 }

f3PtpL3PTPPortStatsEntry OBJECT-TYPE
    SYNTAX      F3PtpL3PTPPortStatsEntry 
    MAX-ACCESS  not-accessible
    STATUS      current
    DESCRIPTION
            "A conceptual row in the f3PtpL3PTPPortStatsTable.
             Entries exist in this table for each L3 PTP Port."
    INDEX { neIndex, f3PtpPTPClockIndex, f3PtpL3PTPPortIndex, f3PtpL3PTPPortStatsIndex }
 
    ::= { f3PtpL3PTPPortStatsTable 1 }

F3PtpL3PTPPortStatsEntry ::= SEQUENCE {
    f3PtpL3PTPPortStatsIndex                        Integer32,
    f3PtpL3PTPPortStatsIntervalType                 CmPmIntervalType,
    f3PtpL3PTPPortStatsValid                        TruthValue,
    f3PtpL3PTPPortStatsAction                       CmPmBinAction,
    f3PtpL3PTPPortStatsAvgAnnounceRate              Unsigned32,
    f3PtpL3PTPPortStatsAvgSyncRate                  Unsigned32,
    f3PtpL3PTPPortStatsAvgDelayReqRate              Unsigned32,
    f3PtpL3PTPPortStatsAvgDelayRespRate             Unsigned32,
    f3PtpL3PTPPortStatsMismatchDomainDiscards       PerfCounter64,
    f3PtpL3PTPPortStatsMessageWrongTypeDiscards     PerfCounter64,
    f3PtpL3PTPPortStatsMessagesWrongLengthDiscards  PerfCounter64,
    f3PtpL3PTPPortStatsUnknownMasterDiscards        PerfCounter64,
    f3PtpL3PTPPortStatsMinOffsetFromMaster          PerfCounter64,
    f3PtpL3PTPPortStatsMaxOffsetFromMaster          PerfCounter64,
    f3PtpL3PTPPortStatsAvgOffsetFromMaster          PerfCounter64,
    f3PtpL3PTPPortStatsMinSyncPathDelay             PerfCounter64,
    f3PtpL3PTPPortStatsMaxSyncPathDelay             PerfCounter64,
    f3PtpL3PTPPortStatsAvgSyncPathDelay             PerfCounter64,
    f3PtpL3PTPPortStatsMinMeanPathDelay             PerfCounter64,
    f3PtpL3PTPPortStatsMaxMeanPathDelay             PerfCounter64,
    f3PtpL3PTPPortStatsAvgMeanPathDelay             PerfCounter64,
    f3PtpL3PTPPortStatsMsgMiscDiscards              PerfCounter64
}

f3PtpL3PTPPortStatsIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpL3PTPPortStatsEntry 1 }

f3PtpL3PTPPortStatsIntervalType OBJECT-TYPE
    SYNTAX      CmPmIntervalType
    MAX-ACCESS  read-only
    STATUS      current
    DESCRIPTION
            "Indicates the type of collection, i.e. whether it is
             15 Min, 1 Day or rollover."
    ::= { f3PtpL3PTPPortStatsEntry 2 }

f3PtpL3PTPPortStatsValid OBJECT-TYPE
    SYNTAX      TruthValue
    MAX-ACCESS  read-only
    STATUS      current
    DESCRIPTION
            "Indicates the validity of the bin."
    ::= { f3PtpL3PTPPortStatsEntry 3 }

f3PtpL3PTPPortStatsAction OBJECT-TYPE
    SYNTAX      CmPmBinAction
    MAX-ACCESS  read-write
    STATUS      current
    DESCRIPTION
            "Allows the Manager to clear the bin."
    ::= { f3PtpL3PTPPortStatsEntry 4 }

f3PtpL3PTPPortStatsAvgAnnounceRate OBJECT-TYPE
     SYNTAX     Unsigned32
     MAX-ACCESS read-only
     STATUS     current
     DESCRIPTION
         "Avg Announce Rate."
     ::= { f3PtpL3PTPPortStatsEntry 5 }

f3PtpL3PTPPortStatsAvgSyncRate OBJECT-TYPE
     SYNTAX     Unsigned32
     MAX-ACCESS read-only
     STATUS     current
     DESCRIPTION
         "Avg Sync Rate."
     ::= { f3PtpL3PTPPortStatsEntry 6 }

f3PtpL3PTPPortStatsAvgDelayReqRate OBJECT-TYPE
     SYNTAX     Unsigned32
     MAX-ACCESS read-only
     STATUS     current
     DESCRIPTION
         "Avg Delay Req Rate."
     ::= { f3PtpL3PTPPortStatsEntry 7 }

f3PtpL3PTPPortStatsAvgDelayRespRate OBJECT-TYPE
     SYNTAX     Unsigned32
     MAX-ACCESS read-only
     STATUS     current
     DESCRIPTION
         "Avg Delay Resp Rate."
     ::= { f3PtpL3PTPPortStatsEntry 8 }

f3PtpL3PTPPortStatsMismatchDomainDiscards OBJECT-TYPE
     SYNTAX     PerfCounter64
     MAX-ACCESS read-only
     STATUS     current
     DESCRIPTION
         "Mismatch Domain Discards."
     ::= { f3PtpL3PTPPortStatsEntry 9 }

f3PtpL3PTPPortStatsMessageWrongTypeDiscards OBJECT-TYPE
     SYNTAX     PerfCounter64
     MAX-ACCESS read-only
     STATUS     current
     DESCRIPTION
         "Message Wrong Type Discards."
     ::= { f3PtpL3PTPPortStatsEntry 10 }

f3PtpL3PTPPortStatsMessagesWrongLengthDiscards OBJECT-TYPE
     SYNTAX     PerfCounter64
     MAX-ACCESS read-only
     STATUS     current
     DESCRIPTION
         "Messages Wrong Length Discards."
     ::= { f3PtpL3PTPPortStatsEntry 11 }

f3PtpL3PTPPortStatsUnknownMasterDiscards OBJECT-TYPE
     SYNTAX     PerfCounter64
     MAX-ACCESS read-only
     STATUS     deprecated
     DESCRIPTION
         "Unknown Master Discards."
     ::= { f3PtpL3PTPPortStatsEntry 12 }

f3PtpL3PTPPortStatsMinOffsetFromMaster OBJECT-TYPE
     SYNTAX     PerfCounter64
     MAX-ACCESS read-only
     STATUS     current
     DESCRIPTION
         "Min Offset From Master."
     ::= { f3PtpL3PTPPortStatsEntry 13 }

f3PtpL3PTPPortStatsMaxOffsetFromMaster OBJECT-TYPE
     SYNTAX     PerfCounter64
     MAX-ACCESS read-only
     STATUS     current
     DESCRIPTION
         "Max Offset From Master."
     ::= { f3PtpL3PTPPortStatsEntry 14 }

f3PtpL3PTPPortStatsAvgOffsetFromMaster OBJECT-TYPE
     SYNTAX     PerfCounter64
     MAX-ACCESS read-only
     STATUS     current
     DESCRIPTION
         "Avg Offset From Master."
     ::= { f3PtpL3PTPPortStatsEntry 15 }

f3PtpL3PTPPortStatsMinSyncPathDelay OBJECT-TYPE
     SYNTAX     PerfCounter64
     MAX-ACCESS read-only
     STATUS     current
     DESCRIPTION
         "Min Sync Path Delay."
     ::= { f3PtpL3PTPPortStatsEntry 16 }

f3PtpL3PTPPortStatsMaxSyncPathDelay OBJECT-TYPE
     SYNTAX     PerfCounter64
     MAX-ACCESS read-only
     STATUS     current
     DESCRIPTION
         "Max Sync Path Delay."
     ::= { f3PtpL3PTPPortStatsEntry 17 }

f3PtpL3PTPPortStatsAvgSyncPathDelay OBJECT-TYPE
     SYNTAX     PerfCounter64
     MAX-ACCESS read-only
     STATUS     current
     DESCRIPTION
         "Avg Sync Path Delay."
     ::= { f3PtpL3PTPPortStatsEntry 18 }


f3PtpL3PTPPortStatsMinMeanPathDelay OBJECT-TYPE
     SYNTAX     PerfCounter64
     MAX-ACCESS read-only
     STATUS     current
     DESCRIPTION
         "Min Mean Path Delay."
     ::= { f3PtpL3PTPPortStatsEntry 19 }

f3PtpL3PTPPortStatsMaxMeanPathDelay OBJECT-TYPE
     SYNTAX     PerfCounter64
     MAX-ACCESS read-only
     STATUS     current
     DESCRIPTION
         "Max Mean Path Delay."
     ::= { f3PtpL3PTPPortStatsEntry 20 }

f3PtpL3PTPPortStatsAvgMeanPathDelay OBJECT-TYPE
     SYNTAX     PerfCounter64
     MAX-ACCESS read-only
     STATUS     current
     DESCRIPTION
         "Avg Mean Path Delay."
     ::= { f3PtpL3PTPPortStatsEntry 21 }

f3PtpL3PTPPortStatsMsgMiscDiscards OBJECT-TYPE
     SYNTAX     PerfCounter64
     MAX-ACCESS read-only
     STATUS     deprecated
     DESCRIPTION
         "Number of received packets discarded due to miscellaneous reasons."
     ::= { f3PtpL3PTPPortStatsEntry 22 }

--
-- L3 PTP Port Current History Table
--
f3PtpL3PTPPortHistoryTable OBJECT-TYPE
    SYNTAX      SEQUENCE OF F3PtpL3PTPPortHistoryEntry
    MAX-ACCESS  not-accessible
    STATUS      current
    DESCRIPTION
            "A collection of PTP Port related statistics.  
             These reflect the current data."
    ::= { f3PtpPerformanceObjects 29 }

f3PtpL3PTPPortHistoryEntry OBJECT-TYPE
    SYNTAX      F3PtpL3PTPPortHistoryEntry 
    MAX-ACCESS  not-accessible
    STATUS      current
    DESCRIPTION
            "A conceptual row in the f3PtpL3PTPPortHistoryTable.
             Entries exist in this table for each PTP Port."
    INDEX { neIndex, f3PtpPTPClockIndex, f3PtpL3PTPPortIndex,  f3PtpL3PTPPortStatsIndex, f3PtpL3PTPPortHistoryIndex }

    ::= { f3PtpL3PTPPortHistoryTable 1 }

F3PtpL3PTPPortHistoryEntry ::= SEQUENCE {
    f3PtpL3PTPPortHistoryIndex                        Integer32,
    f3PtpL3PTPPortHistoryTime                         DateAndTime,
    f3PtpL3PTPPortHistoryValid                        TruthValue,
    f3PtpL3PTPPortHistoryAction                       CmPmBinAction,
    f3PtpL3PTPPortHistoryAvgAnnounceRate              Unsigned32,
    f3PtpL3PTPPortHistoryAvgSyncRate                  Unsigned32,
    f3PtpL3PTPPortHistoryAvgDelayReqRate              Unsigned32,
    f3PtpL3PTPPortHistoryAvgDelayRespRate             Unsigned32,
    f3PtpL3PTPPortHistoryMismatchDomainDiscards       PerfCounter64,
    f3PtpL3PTPPortHistoryMessageWrongTypeDiscards     PerfCounter64,
    f3PtpL3PTPPortHistoryMessagesWrongLengthDiscards  PerfCounter64,
    f3PtpL3PTPPortHistoryUnknownMasterDiscards        PerfCounter64,
    f3PtpL3PTPPortHistoryMinOffsetFromMaster          PerfCounter64,
    f3PtpL3PTPPortHistoryMaxOffsetFromMaster          PerfCounter64,
    f3PtpL3PTPPortHistoryAvgOffsetFromMaster          PerfCounter64,
    f3PtpL3PTPPortHistoryMinSyncPathDelay             PerfCounter64,
    f3PtpL3PTPPortHistoryMaxSyncPathDelay             PerfCounter64,
    f3PtpL3PTPPortHistoryAvgSyncPathDelay             PerfCounter64,
    f3PtpL3PTPPortHistoryMinMeanPathDelay             PerfCounter64,
    f3PtpL3PTPPortHistoryMaxMeanPathDelay             PerfCounter64,
    f3PtpL3PTPPortHistoryAvgMeanPathDelay             PerfCounter64,
    f3PtpL3PTPPortHistoryMsgMiscDiscards              PerfCounter64
}

f3PtpL3PTPPortHistoryIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpL3PTPPortHistoryEntry 1 }

f3PtpL3PTPPortHistoryTime OBJECT-TYPE
    SYNTAX      DateAndTime
    MAX-ACCESS  read-only
    STATUS      current
    DESCRIPTION
            "Indicates the time of history bin creation." 
    ::= { f3PtpL3PTPPortHistoryEntry 2 }

f3PtpL3PTPPortHistoryValid OBJECT-TYPE
    SYNTAX      TruthValue
    MAX-ACCESS  read-only
    STATUS      current
    DESCRIPTION
            "Indicates the validity of the bin."
    ::= { f3PtpL3PTPPortHistoryEntry 3 }

f3PtpL3PTPPortHistoryAction OBJECT-TYPE
    SYNTAX      CmPmBinAction
    MAX-ACCESS  read-write
    STATUS      current
    DESCRIPTION
            "Allows the Manager to clear the bin."
    ::= { f3PtpL3PTPPortHistoryEntry 4 }

f3PtpL3PTPPortHistoryAvgAnnounceRate OBJECT-TYPE
     SYNTAX     Unsigned32
     MAX-ACCESS read-only
     STATUS     current
     DESCRIPTION
         "Avg Announce Rate."
     ::= { f3PtpL3PTPPortHistoryEntry 5 }

f3PtpL3PTPPortHistoryAvgSyncRate OBJECT-TYPE
     SYNTAX     Unsigned32
     MAX-ACCESS read-only
     STATUS     current
     DESCRIPTION
         "Avg Sync Rate."
     ::= { f3PtpL3PTPPortHistoryEntry 6 }

f3PtpL3PTPPortHistoryAvgDelayReqRate OBJECT-TYPE
     SYNTAX     Unsigned32
     MAX-ACCESS read-only
     STATUS     current
     DESCRIPTION
         "Avg Delay Req Rate."
     ::= { f3PtpL3PTPPortHistoryEntry 7 }

f3PtpL3PTPPortHistoryAvgDelayRespRate OBJECT-TYPE
     SYNTAX     Unsigned32
     MAX-ACCESS read-only
     STATUS     current
     DESCRIPTION
         "Avg Delay Resp Rate."
     ::= { f3PtpL3PTPPortHistoryEntry 8 }

f3PtpL3PTPPortHistoryMismatchDomainDiscards OBJECT-TYPE
     SYNTAX     PerfCounter64
     MAX-ACCESS read-only
     STATUS     current
     DESCRIPTION
         "Mismatch Domain Discards."
     ::= { f3PtpL3PTPPortHistoryEntry 9 }

f3PtpL3PTPPortHistoryMessageWrongTypeDiscards OBJECT-TYPE
     SYNTAX     PerfCounter64
     MAX-ACCESS read-only
     STATUS     current
     DESCRIPTION
         "Message Wrong Type Discards."
     ::= { f3PtpL3PTPPortHistoryEntry 10 }

f3PtpL3PTPPortHistoryMessagesWrongLengthDiscards OBJECT-TYPE
     SYNTAX     PerfCounter64
     MAX-ACCESS read-only
     STATUS     current
     DESCRIPTION
         "Messages Wrong Length Discards."
     ::= { f3PtpL3PTPPortHistoryEntry 11 }

f3PtpL3PTPPortHistoryUnknownMasterDiscards OBJECT-TYPE
     SYNTAX     PerfCounter64
     MAX-ACCESS read-only
     STATUS     deprecated
     DESCRIPTION
         "Unknown Master Discards."
     ::= { f3PtpL3PTPPortHistoryEntry 12 }

f3PtpL3PTPPortHistoryMinOffsetFromMaster OBJECT-TYPE
     SYNTAX     PerfCounter64
     MAX-ACCESS read-only
     STATUS     current
     DESCRIPTION
         "Min Offset From Master."
     ::= { f3PtpL3PTPPortHistoryEntry 13 }

f3PtpL3PTPPortHistoryMaxOffsetFromMaster OBJECT-TYPE
     SYNTAX     PerfCounter64
     MAX-ACCESS read-only
     STATUS     current
     DESCRIPTION
         "Max Offset From Master."
     ::= { f3PtpL3PTPPortHistoryEntry 14 }

f3PtpL3PTPPortHistoryAvgOffsetFromMaster OBJECT-TYPE
     SYNTAX     PerfCounter64
     MAX-ACCESS read-only
     STATUS     current
     DESCRIPTION
         "Avg Offset From Master."
     ::= { f3PtpL3PTPPortHistoryEntry 15 }

f3PtpL3PTPPortHistoryMinSyncPathDelay OBJECT-TYPE
     SYNTAX     PerfCounter64
     MAX-ACCESS read-only
     STATUS     current
     DESCRIPTION
         "Min Sync Path Delay."
     ::= { f3PtpL3PTPPortHistoryEntry 16 }

f3PtpL3PTPPortHistoryMaxSyncPathDelay OBJECT-TYPE
     SYNTAX     PerfCounter64
     MAX-ACCESS read-only
     STATUS     current
     DESCRIPTION
         "Max Sync Path Delay."
     ::= { f3PtpL3PTPPortHistoryEntry 17 }

f3PtpL3PTPPortHistoryAvgSyncPathDelay OBJECT-TYPE
     SYNTAX     PerfCounter64
     MAX-ACCESS read-only
     STATUS     current
     DESCRIPTION
         "Avg Sync Path Delay."
     ::= { f3PtpL3PTPPortHistoryEntry 18 }

f3PtpL3PTPPortHistoryMinMeanPathDelay OBJECT-TYPE
     SYNTAX     PerfCounter64
     MAX-ACCESS read-only
     STATUS     current
     DESCRIPTION
         "Min Mean Path Delay."
     ::= { f3PtpL3PTPPortHistoryEntry 19 }

f3PtpL3PTPPortHistoryMaxMeanPathDelay OBJECT-TYPE
     SYNTAX     PerfCounter64
     MAX-ACCESS read-only
     STATUS     current
     DESCRIPTION
         "Max Mean Path Delay."
     ::= { f3PtpL3PTPPortHistoryEntry 20 }

f3PtpL3PTPPortHistoryAvgMeanPathDelay OBJECT-TYPE
     SYNTAX     PerfCounter64
     MAX-ACCESS read-only
     STATUS     current
     DESCRIPTION
         "Avg Mean Path Delay."
     ::= { f3PtpL3PTPPortHistoryEntry 21 }

f3PtpL3PTPPortHistoryMsgMiscDiscards OBJECT-TYPE
     SYNTAX     PerfCounter64
     MAX-ACCESS read-only
     STATUS     deprecated
     DESCRIPTION
         "Number of received packets discarded due to miscellaneous reasons."
     ::= { f3PtpL3PTPPortHistoryEntry 22 }

--
-- L3 PTP Port Threshold Table
--
f3PtpL3PTPPortThresholdTable OBJECT-TYPE
    SYNTAX      SEQUENCE OF F3PtpL3PTPPortThresholdEntry
    MAX-ACCESS  not-accessible
    STATUS      current
    DESCRIPTION
            "A table of entries that allow manageability of 
             PTP Port Thresholds."
    ::= { f3PtpPerformanceObjects 30 }

f3PtpL3PTPPortThresholdEntry OBJECT-TYPE
    SYNTAX      F3PtpL3PTPPortThresholdEntry
    MAX-ACCESS  not-accessible
    STATUS      current
    DESCRIPTION
            "A conceptual row in the f3PtpL3PTPPortThresholdTable."
    INDEX { neIndex, f3PtpPTPClockIndex, f3PtpL3PTPPortIndex,  
            f3PtpL3PTPPortStatsIndex, f3PtpL3PTPPortThresholdIndex }
    ::= { f3PtpL3PTPPortThresholdTable 1 }

F3PtpL3PTPPortThresholdEntry ::= SEQUENCE {
    f3PtpL3PTPPortThresholdIndex       Integer32,
    f3PtpL3PTPPortThresholdInterval    CmPmIntervalType,
    f3PtpL3PTPPortThresholdVariable    VariablePointer,
    f3PtpL3PTPPortThresholdValueLo     Unsigned32,
    f3PtpL3PTPPortThresholdValueHi     Unsigned32,
    f3PtpL3PTPPortThresholdMonValue    PerfCounter64
}

f3PtpL3PTPPortThresholdIndex OBJECT-TYPE
    SYNTAX     Integer32 (1..65535)
    MAX-ACCESS not-accessible
    STATUS     current
    DESCRIPTION
        "An index that uniquely identifies an entry in the
        f3PtpL3PTPPortThresholdTable."
    ::= { f3PtpL3PTPPortThresholdEntry 1 }

f3PtpL3PTPPortThresholdInterval OBJECT-TYPE
    SYNTAX     CmPmIntervalType
    MAX-ACCESS read-only
    STATUS     current
    DESCRIPTION
        "The interval over which monitored value is
        sampled and compared with the specified threshold."
    ::= { f3PtpL3PTPPortThresholdEntry 2 }

f3PtpL3PTPPortThresholdVariable OBJECT-TYPE
    SYNTAX     VariablePointer
    MAX-ACCESS read-only
    STATUS     current
    DESCRIPTION
        "The object identifier of the particular variable to be
        sampled."
    ::= { f3PtpL3PTPPortThresholdEntry 3 }

f3PtpL3PTPPortThresholdValueLo OBJECT-TYPE
    SYNTAX     Unsigned32
    MAX-ACCESS read-write
    STATUS     current
    DESCRIPTION
        "Lower 32 bits of the threshold value."
    ::= { f3PtpL3PTPPortThresholdEntry 4 }

f3PtpL3PTPPortThresholdValueHi OBJECT-TYPE
    SYNTAX     Unsigned32
    MAX-ACCESS read-write
    STATUS     current
    DESCRIPTION
        "Higher 32 bits of the threshold value."
    ::= { f3PtpL3PTPPortThresholdEntry 5 }

f3PtpL3PTPPortThresholdMonValue OBJECT-TYPE
    SYNTAX     PerfCounter64
    MAX-ACCESS read-only
    STATUS     current
    DESCRIPTION
        "Monitored value corresponding to f3PtpL3PTPPortThresholdVariable."
    ::= { f3PtpL3PTPPortThresholdEntry 6 }



--
-- Ptp L3 PTP Port Stats Data Table
--
f3PtpL3PTPPortStatsV2Table  OBJECT-TYPE
    SYNTAX      SEQUENCE OF F3PtpL3PTPPortStatsV2Entry
    MAX-ACCESS  not-accessible
    STATUS      current
    DESCRIPTION
        "A list of Ptp L3 PTP Port Current Data fsp150 family of products."
    ::= { f3PtpPerformanceObjects 31 }

f3PtpL3PTPPortStatsV2Entry  OBJECT-TYPE
    SYNTAX      F3PtpL3PTPPortStatsV2Entry
    MAX-ACCESS  not-accessible
    STATUS      current
    DESCRIPTION
        "A conceptual row in the f3PtpL3PTPPortStatsV2Table. Entries can
        be created/deleted in this table by management application action."

    AUGMENTS { f3PtpL3PTPPortStatsEntry }

    ::= { f3PtpL3PTPPortStatsV2Table 1 }

F3PtpL3PTPPortStatsV2Entry ::= SEQUENCE {
      f3PtpL3PTPPortStatsV2IntervalType                    CmPmIntervalType,
      f3PtpL3PTPPortStatsV2ValidFlag                       TruthValue,
      f3PtpL3PTPPortStatsV2Action                          CmPmBinAction,
      f3PtpL3PTPPortStatsV2OutOfSequenceAnnouceMessages    PerfCounter64,
      f3PtpL3PTPPortStatsV2OutOfSequenceSyncMessages       PerfCounter64,
      f3PtpL3PTPPortStatsV2MgmtMessagesDiscards            PerfCounter64,
      f3PtpL3PTPPortStatsV2AnnounceDeniedEventsTx          PerfCounter64,
      f3PtpL3PTPPortStatsV2SyncDeniedEventsTx              PerfCounter64,
      f3PtpL3PTPPortStatsV2DynamicSlavesLearnedCount       PerfCounter64,
      f3PtpL3PTPPortStatsV2DynamicSlavesDropped            PerfCounter64,
      f3PtpL3PTPPortStatsV2DelayRespDeniedEventsTx         PerfCounter64,
      f3PtpL3PTPPortStatsV2AnnounceCancelledEventsTx       PerfCounter64,
      f3PtpL3PTPPortStatsV2SyncCancelledEventsTx           PerfCounter64,
      f3PtpL3PTPPortStatsV2DelayRespCancelledEventsTx      PerfCounter64,
      f3PtpL3PTPPortStatsV2AnnounceDeniedEventsRx          PerfCounter64,
      f3PtpL3PTPPortStatsV2SyncDeniedEventsRx              PerfCounter64,
      f3PtpL3PTPPortStatsV2DelayRespDeniedEventsRx         PerfCounter64,
      f3PtpL3PTPPortStatsV2AnnounceCancelledEventsRx       PerfCounter64,
      f3PtpL3PTPPortStatsV2SyncCancelledEventsRx           PerfCounter64,
      f3PtpL3PTPPortStatsV2DelayRespCancelledEventsRx      PerfCounter64,
      f3PtpL3PTPPortStatsV2AnnouncesRx                     PerfCounter64,
      f3PtpL3PTPPortStatsV2AnnouncesTx                     PerfCounter64,
      f3PtpL3PTPPortStatsV2SyncsRx                         PerfCounter64,
      f3PtpL3PTPPortStatsV2SyncsTx                         PerfCounter64,
      f3PtpL3PTPPortStatsV2FollowupsRx                     PerfCounter64,
      f3PtpL3PTPPortStatsV2FollowupsTx                     PerfCounter64,
      f3PtpL3PTPPortStatsV2DelayReqsRx                     PerfCounter64,
      f3PtpL3PTPPortStatsV2DelayReqsTx                     PerfCounter64,
      f3PtpL3PTPPortStatsV2DelayRspsRx                     PerfCounter64,
      f3PtpL3PTPPortStatsV2DelayRspsTx                     PerfCounter64,
      f3PtpL3PTPPortStatsV2SignalingRx                     PerfCounter64,
      f3PtpL3PTPPortStatsV2SignalingTx                     PerfCounter64,
      f3PtpL3PTPPortStatsV2MgmtFramesRx                    PerfCounter64,
      f3PtpL3PTPPortStatsV2MgmtFramesTx                    PerfCounter64,
      f3PtpL3PTPPortStatsV2PtpUnknownsRx                   PerfCounter64,
      f3PtpL3PTPPortStatsV2AvgSyncResTime                  Unsigned32,
      f3PtpL3PTPPortStatsV2MinSyncResTime                  Unsigned32,
      f3PtpL3PTPPortStatsV2MaxSyncResTime                  Unsigned32,
      f3PtpL3PTPPortStatsV2AvgDelayReqResTime              Unsigned32,
      f3PtpL3PTPPortStatsV2MinDelayReqResTime              Unsigned32,
      f3PtpL3PTPPortStatsV2MaxDelayReqResTime              Unsigned32,
      f3PtpL3PTPPortStatsV2AvgAnnounceRate                 Unsigned32,
      f3PtpL3PTPPortStatsV2AvgSyncRate                     Unsigned32,
      f3PtpL3PTPPortStatsV2AvgDelayReqRate                 Unsigned32,
      f3PtpL3PTPPortStatsV2AvgDelayRespRate                Unsigned32,
      f3PtpL3PTPPortStatsV2MismatchDomainDiscards          PerfCounter64,
      f3PtpL3PTPPortStatsV2MessageWrongTypeDiscards        PerfCounter64,
      f3PtpL3PTPPortStatsV2MessagesWrongLengthDiscards     PerfCounter64,
      f3PtpL3PTPPortStatsV2UnknownMasterDiscards           PerfCounter64,
      f3PtpL3PTPPortStatsV2MessageMiscDiscards             PerfCounter64
    }

f3PtpL3PTPPortStatsV2IntervalType OBJECT-TYPE
    SYNTAX      CmPmIntervalType 
    MAX-ACCESS  read-only
    STATUS      current
    DESCRIPTION
        "Interval Type of L3 PTP Port Current Data."
    ::= { f3PtpL3PTPPortStatsV2Entry 1 }

f3PtpL3PTPPortStatsV2ValidFlag OBJECT-TYPE
    SYNTAX      TruthValue 
    MAX-ACCESS  read-only
    STATUS      current
    DESCRIPTION
        "Valid Flag of L3 PTP Port Current Data."
    ::= { f3PtpL3PTPPortStatsV2Entry 2 }

f3PtpL3PTPPortStatsV2Action OBJECT-TYPE
    SYNTAX      CmPmBinAction 
    MAX-ACCESS  read-write
    STATUS      current
    DESCRIPTION
        "Action of L3 PTP Port Current Data."
    ::= { f3PtpL3PTPPortStatsV2Entry 3 }

f3PtpL3PTPPortStatsV2OutOfSequenceAnnouceMessages OBJECT-TYPE
    SYNTAX      PerfCounter64 
    MAX-ACCESS  read-only
    STATUS      current
    DESCRIPTION
        "Out of sequence Announce messages."
    ::= { f3PtpL3PTPPortStatsV2Entry 4 }

f3PtpL3PTPPortStatsV2OutOfSequenceSyncMessages OBJECT-TYPE
    SYNTAX      PerfCounter64 
    MAX-ACCESS  read-only
    STATUS      current
    DESCRIPTION
        "Out of sequence Sync messages."
    ::= { f3PtpL3PTPPortStatsV2Entry 5 }

f3PtpL3PTPPortStatsV2MgmtMessagesDiscards OBJECT-TYPE
    SYNTAX      PerfCounter64 
    MAX-ACCESS  read-only
    STATUS      current
    DESCRIPTION
        "Management messages discarded."
    ::= { f3PtpL3PTPPortStatsV2Entry 6 }

f3PtpL3PTPPortStatsV2AnnounceDeniedEventsTx OBJECT-TYPE
    SYNTAX      PerfCounter64 
    MAX-ACCESS  read-only
    STATUS      current
    DESCRIPTION
        "Announce Service Denied Events Transmitted."
    ::= { f3PtpL3PTPPortStatsV2Entry 7 }

f3PtpL3PTPPortStatsV2SyncDeniedEventsTx OBJECT-TYPE
    SYNTAX      PerfCounter64 
    MAX-ACCESS  read-only
    STATUS      current
    DESCRIPTION
        "Sync Service Denied Events?Transmitted."
    ::= { f3PtpL3PTPPortStatsV2Entry 8 }

f3PtpL3PTPPortStatsV2DynamicSlavesLearnedCount OBJECT-TYPE
    SYNTAX      PerfCounter64 
    MAX-ACCESS  read-only
    STATUS      current
    DESCRIPTION
        "Dynamic Slaves Services Learned Count."
    ::= { f3PtpL3PTPPortStatsV2Entry 9 }

f3PtpL3PTPPortStatsV2DynamicSlavesDropped OBJECT-TYPE
    SYNTAX      PerfCounter64 
    MAX-ACCESS  read-only
    STATUS      current
    DESCRIPTION
        "Dynamic Slaves Service Dropped."
    ::= { f3PtpL3PTPPortStatsV2Entry 10 }

f3PtpL3PTPPortStatsV2DelayRespDeniedEventsTx OBJECT-TYPE
    SYNTAX      PerfCounter64 
    MAX-ACCESS  read-only
    STATUS      current
    DESCRIPTION
        "Delay Response Service Denied Events Transmitted."
    ::= { f3PtpL3PTPPortStatsV2Entry 11 }

f3PtpL3PTPPortStatsV2AnnounceCancelledEventsTx OBJECT-TYPE
    SYNTAX      PerfCounter64 
    MAX-ACCESS  read-only
    STATUS      current
    DESCRIPTION
        "Announce Service Cancelled Events Transmitted."
    ::= { f3PtpL3PTPPortStatsV2Entry 12 }

f3PtpL3PTPPortStatsV2SyncCancelledEventsTx OBJECT-TYPE
    SYNTAX      PerfCounter64 
    MAX-ACCESS  read-only
    STATUS      current
    DESCRIPTION
        "Sync Service Cancelled Events Transmitted."
    ::= { f3PtpL3PTPPortStatsV2Entry 13 }

f3PtpL3PTPPortStatsV2DelayRespCancelledEventsTx OBJECT-TYPE
    SYNTAX      PerfCounter64 
    MAX-ACCESS  read-only
    STATUS      current
    DESCRIPTION
        "Delay Response Service Cancelled Events Transmitted."
    ::= { f3PtpL3PTPPortStatsV2Entry 14 }

f3PtpL3PTPPortStatsV2AnnounceDeniedEventsRx OBJECT-TYPE
    SYNTAX      PerfCounter64 
    MAX-ACCESS  read-only
    STATUS      current
    DESCRIPTION
        "Announce Service Denied Events Received."
    ::= { f3PtpL3PTPPortStatsV2Entry 15 }

f3PtpL3PTPPortStatsV2SyncDeniedEventsRx OBJECT-TYPE
    SYNTAX      PerfCounter64 
    MAX-ACCESS  read-only
    STATUS      current
    DESCRIPTION
        "Sync Service Denied Events?Received."
    ::= { f3PtpL3PTPPortStatsV2Entry 16 }

f3PtpL3PTPPortStatsV2DelayRespDeniedEventsRx OBJECT-TYPE
    SYNTAX      PerfCounter64 
    MAX-ACCESS  read-only
    STATUS      current
    DESCRIPTION
        "Delay Response Service Denied Events Received."
    ::= { f3PtpL3PTPPortStatsV2Entry 17 }

f3PtpL3PTPPortStatsV2AnnounceCancelledEventsRx OBJECT-TYPE
    SYNTAX      PerfCounter64 
    MAX-ACCESS  read-only
    STATUS      current
    DESCRIPTION
        "Announce Service Cancelled Events Received."
    ::= { f3PtpL3PTPPortStatsV2Entry 18 }

f3PtpL3PTPPortStatsV2SyncCancelledEventsRx OBJECT-TYPE
    SYNTAX      PerfCounter64 
    MAX-ACCESS  read-only
    STATUS      current
    DESCRIPTION
        "Sync Service Cancelled Events Received."
    ::= { f3PtpL3PTPPortStatsV2Entry 19 }

f3PtpL3PTPPortStatsV2DelayRespCancelledEventsRx OBJECT-TYPE
    SYNTAX      PerfCounter64 
    MAX-ACCESS  read-only
    STATUS      current
    DESCRIPTION
        "Delay Response Service Cancelled Events Received."
    ::= { f3PtpL3PTPPortStatsV2Entry 20 }

f3PtpL3PTPPortStatsV2AnnouncesRx OBJECT-TYPE
    SYNTAX      PerfCounter64 
    MAX-ACCESS  read-only
    STATUS      current
    DESCRIPTION
        "Announces Rx of L3 PTP Port Current Data."
    ::= { f3PtpL3PTPPortStatsV2Entry 21 }

f3PtpL3PTPPortStatsV2AnnouncesTx OBJECT-TYPE
    SYNTAX      PerfCounter64 
    MAX-ACCESS  read-only
    STATUS      current
    DESCRIPTION
        "Announces Tx of L3 PTP Port Current Data."
    ::= { f3PtpL3PTPPortStatsV2Entry 22 }

f3PtpL3PTPPortStatsV2SyncsRx OBJECT-TYPE
    SYNTAX      PerfCounter64 
    MAX-ACCESS  read-only
    STATUS      current
    DESCRIPTION
        "Syncs Rx of L3 PTP Port Current Data."
    ::= { f3PtpL3PTPPortStatsV2Entry 23 }

f3PtpL3PTPPortStatsV2SyncsTx OBJECT-TYPE
    SYNTAX      PerfCounter64 
    MAX-ACCESS  read-only
    STATUS      current
    DESCRIPTION
        "Syncs Tx of L3 PTP Port Current Data."
    ::= { f3PtpL3PTPPortStatsV2Entry 24 }

f3PtpL3PTPPortStatsV2FollowupsRx OBJECT-TYPE
    SYNTAX      PerfCounter64 
    MAX-ACCESS  read-only
    STATUS      current
    DESCRIPTION
        "Followups Rx of L3 PTP Port Current Data."
    ::= { f3PtpL3PTPPortStatsV2Entry 25 }

f3PtpL3PTPPortStatsV2FollowupsTx OBJECT-TYPE
    SYNTAX      PerfCounter64 
    MAX-ACCESS  read-only
    STATUS      current
    DESCRIPTION
        "Followups Tx of L3 PTP Port Current Data."
    ::= { f3PtpL3PTPPortStatsV2Entry 26 }

f3PtpL3PTPPortStatsV2DelayReqsRx OBJECT-TYPE
    SYNTAX      PerfCounter64 
    MAX-ACCESS  read-only
    STATUS      current
    DESCRIPTION
        "Delay Reqs Rx of L3 PTP Port Current Data."
    ::= { f3PtpL3PTPPortStatsV2Entry 27 }

f3PtpL3PTPPortStatsV2DelayReqsTx OBJECT-TYPE
    SYNTAX      PerfCounter64 
    MAX-ACCESS  read-only
    STATUS      current
    DESCRIPTION
        "Delay Reqs Tx of L3 PTP Port Current Data."
    ::= { f3PtpL3PTPPortStatsV2Entry 28 }

f3PtpL3PTPPortStatsV2DelayRspsRx OBJECT-TYPE
    SYNTAX      PerfCounter64 
    MAX-ACCESS  read-only
    STATUS      current
    DESCRIPTION
        "Delay Rsps Rx of L3 PTP Port Current Data."
    ::= { f3PtpL3PTPPortStatsV2Entry 29 }

f3PtpL3PTPPortStatsV2DelayRspsTx OBJECT-TYPE
    SYNTAX      PerfCounter64 
    MAX-ACCESS  read-only
    STATUS      current
    DESCRIPTION
        "Delay Rsps Tx of L3 PTP Port Current Data."
    ::= { f3PtpL3PTPPortStatsV2Entry 30 }

f3PtpL3PTPPortStatsV2SignalingRx OBJECT-TYPE
    SYNTAX      PerfCounter64 
    MAX-ACCESS  read-only
    STATUS      current
    DESCRIPTION
        "Signaling Rx of L3 PTP Port Current Data."
    ::= { f3PtpL3PTPPortStatsV2Entry 31 }

f3PtpL3PTPPortStatsV2SignalingTx OBJECT-TYPE
    SYNTAX      PerfCounter64 
    MAX-ACCESS  read-only
    STATUS      current
    DESCRIPTION
        "Signaling Tx of L3 PTP Port Current Data."
    ::= { f3PtpL3PTPPortStatsV2Entry 32 }

f3PtpL3PTPPortStatsV2MgmtFramesRx OBJECT-TYPE
    SYNTAX      PerfCounter64 
    MAX-ACCESS  read-only
    STATUS      current
    DESCRIPTION
        "Mgmt Frames Rx of L3 PTP Port Current Data."
    ::= { f3PtpL3PTPPortStatsV2Entry 33 }

f3PtpL3PTPPortStatsV2MgmtFramesTx OBJECT-TYPE
    SYNTAX      PerfCounter64 
    MAX-ACCESS  read-only
    STATUS      current
    DESCRIPTION
        "Mgmt Frames Tx of L3 PTP Port Current Data."
    ::= { f3PtpL3PTPPortStatsV2Entry 34 }

f3PtpL3PTPPortStatsV2PtpUnknownsRx OBJECT-TYPE
    SYNTAX      PerfCounter64 
    MAX-ACCESS  read-only
    STATUS      current
    DESCRIPTION
        "Ptp Unknowns Rx of L3 PTP Port Current Data."
    ::= { f3PtpL3PTPPortStatsV2Entry 35 }

f3PtpL3PTPPortStatsV2AvgSyncResTime OBJECT-TYPE
    SYNTAX      Unsigned32 
    MAX-ACCESS  read-only
    STATUS      current
    DESCRIPTION
        "Avg Sync Res Time of L3 PTP Port Current Data."
    ::= { f3PtpL3PTPPortStatsV2Entry 36 }

f3PtpL3PTPPortStatsV2MinSyncResTime OBJECT-TYPE
    SYNTAX      Unsigned32 
    MAX-ACCESS  read-only
    STATUS      current
    DESCRIPTION
        "Min Sync Res Time of L3 PTP Port Current Data."
    ::= { f3PtpL3PTPPortStatsV2Entry 37 }

f3PtpL3PTPPortStatsV2MaxSyncResTime OBJECT-TYPE
    SYNTAX      Unsigned32 
    MAX-ACCESS  read-only
    STATUS      current
    DESCRIPTION
        "Max Sync Res Time of L3 PTP Port Current Data."
    ::= { f3PtpL3PTPPortStatsV2Entry 38 }

f3PtpL3PTPPortStatsV2AvgDelayReqResTime OBJECT-TYPE
    SYNTAX      Unsigned32 
    MAX-ACCESS  read-only
    STATUS      current
    DESCRIPTION
        "Avg Delay Req Res Time of L3 PTP Port Current Data."
    ::= { f3PtpL3PTPPortStatsV2Entry 39 }

f3PtpL3PTPPortStatsV2MinDelayReqResTime OBJECT-TYPE
    SYNTAX      Unsigned32 
    MAX-ACCESS  read-only
    STATUS      current
    DESCRIPTION
        "Min Delay Req Res Time of L3 PTP Port Current Data."
    ::= { f3PtpL3PTPPortStatsV2Entry 40 }

f3PtpL3PTPPortStatsV2MaxDelayReqResTime OBJECT-TYPE
    SYNTAX      Unsigned32 
    MAX-ACCESS  read-only
    STATUS      current
    DESCRIPTION
        "Max Delay Req Res Time of L3 PTP Port Current Data."
    ::= { f3PtpL3PTPPortStatsV2Entry 41 }

f3PtpL3PTPPortStatsV2AvgAnnounceRate OBJECT-TYPE
    SYNTAX      Unsigned32 
    MAX-ACCESS  read-only
    STATUS      current
    DESCRIPTION
        "Avg Announce Rate of L3 PTP Port Current Data."
    ::= { f3PtpL3PTPPortStatsV2Entry 42 }

f3PtpL3PTPPortStatsV2AvgSyncRate OBJECT-TYPE
    SYNTAX      Unsigned32 
    MAX-ACCESS  read-only
    STATUS      current
    DESCRIPTION
        "Avg Sync Rate of L3 PTP Port Current Data."
    ::= { f3PtpL3PTPPortStatsV2Entry 43 }

f3PtpL3PTPPortStatsV2AvgDelayReqRate OBJECT-TYPE
    SYNTAX      Unsigned32 
    MAX-ACCESS  read-only
    STATUS      current
    DESCRIPTION
        "Avg Delay Req Rate of L3 PTP Port Current Data."
    ::= { f3PtpL3PTPPortStatsV2Entry 44 }

f3PtpL3PTPPortStatsV2AvgDelayRespRate OBJECT-TYPE
    SYNTAX      Unsigned32 
    MAX-ACCESS  read-only
    STATUS      current
    DESCRIPTION
        "Avg Delay Resp Rate of L3 PTP Port Current Data."
    ::= { f3PtpL3PTPPortStatsV2Entry 45 }

f3PtpL3PTPPortStatsV2MismatchDomainDiscards OBJECT-TYPE
    SYNTAX      PerfCounter64 
    MAX-ACCESS  read-only
    STATUS      current
    DESCRIPTION
        "Mismatch Domain Discards of L3 PTP Port Current Data."
    ::= { f3PtpL3PTPPortStatsV2Entry 46 }

f3PtpL3PTPPortStatsV2MessageWrongTypeDiscards OBJECT-TYPE
    SYNTAX      PerfCounter64 
    MAX-ACCESS  read-only
    STATUS      current
    DESCRIPTION
        "Message Wrong Type Discards of L3 PTP Port Current Data."
    ::= { f3PtpL3PTPPortStatsV2Entry 47 }

f3PtpL3PTPPortStatsV2MessagesWrongLengthDiscards OBJECT-TYPE
    SYNTAX      PerfCounter64 
    MAX-ACCESS  read-only
    STATUS      current
    DESCRIPTION
        "Messages Wrong Length Discards of L3 PTP Port Current Data."
    ::= { f3PtpL3PTPPortStatsV2Entry 48 }

f3PtpL3PTPPortStatsV2UnknownMasterDiscards OBJECT-TYPE
    SYNTAX      PerfCounter64 
    MAX-ACCESS  read-only
    STATUS      current
    DESCRIPTION
        "Unknown Master Discards of L3 PTP Port Current Data."
    ::= { f3PtpL3PTPPortStatsV2Entry 49 }

f3PtpL3PTPPortStatsV2MessageMiscDiscards OBJECT-TYPE
    SYNTAX      PerfCounter64 
    MAX-ACCESS  read-only
    STATUS      current
    DESCRIPTION
        "Message Misc Discards of L3 PTP Port Current Data."
    ::= { f3PtpL3PTPPortStatsV2Entry 50 }


--
-- Ptp L3 PTP Port History Table
--
f3PtpL3PTPPortHistoryV2Table  OBJECT-TYPE
    SYNTAX      SEQUENCE OF F3PtpL3PTPPortHistoryV2Entry
    MAX-ACCESS  not-accessible
    STATUS      current
    DESCRIPTION
        "A list of Ptp L3 PTP Port History Data fsp150 family of products."
    ::= { f3PtpPerformanceObjects 32 }

f3PtpL3PTPPortHistoryV2Entry  OBJECT-TYPE
    SYNTAX      F3PtpL3PTPPortHistoryV2Entry
    MAX-ACCESS  not-accessible
    STATUS      current
    DESCRIPTION
        "A conceptual row in the f3PtpL3PTPPortHistoryV2Table. Entries can
        be created/deleted in this table by management application action."
    
    AUGMENTS { f3PtpL3PTPPortHistoryEntry }

    ::= { f3PtpL3PTPPortHistoryV2Table 1 }

F3PtpL3PTPPortHistoryV2Entry ::= SEQUENCE {
      f3PtpL3PTPPortHistoryV2IntervalType                    CmPmIntervalType,
      f3PtpL3PTPPortHistoryV2TimeStamp                       DateAndTime,
      f3PtpL3PTPPortHistoryV2ValidFlag                       TruthValue,
      f3PtpL3PTPPortHistoryV2Action                          CmPmBinAction,
      f3PtpL3PTPPortHistoryV2OutOfSequenceAnnouceMessages    PerfCounter64,
      f3PtpL3PTPPortHistoryV2OutOfSequenceSyncMessages       PerfCounter64,
      f3PtpL3PTPPortHistoryV2MgmtMessagesDiscards            PerfCounter64,
      f3PtpL3PTPPortHistoryV2AnnounceDeniedEventsTx          PerfCounter64,
      f3PtpL3PTPPortHistoryV2SyncDeniedEventsTx              PerfCounter64,
      f3PtpL3PTPPortHistoryV2DynamicSlavesLearnedCount       PerfCounter64,
      f3PtpL3PTPPortHistoryV2DynamicSlavesDropped            PerfCounter64,
      f3PtpL3PTPPortHistoryV2DelayRespDeniedEventsTx         PerfCounter64,
      f3PtpL3PTPPortHistoryV2AnnounceCancelledEventsTx       PerfCounter64,
      f3PtpL3PTPPortHistoryV2SyncCancelledEventsTx           PerfCounter64,
      f3PtpL3PTPPortHistoryV2DelayRespCancelledEventsTx      PerfCounter64,
      f3PtpL3PTPPortHistoryV2AnnounceDeniedEventsRx          PerfCounter64,
      f3PtpL3PTPPortHistoryV2SyncDeniedEventsRx              PerfCounter64,
      f3PtpL3PTPPortHistoryV2DelayRespDeniedEventsRx         PerfCounter64,
      f3PtpL3PTPPortHistoryV2AnnounceCancelledEventsRx       PerfCounter64,
      f3PtpL3PTPPortHistoryV2SyncCancelledEventsRx           PerfCounter64,
      f3PtpL3PTPPortHistoryV2DelayRespCancelledEventsRx      PerfCounter64,
      f3PtpL3PTPPortHistoryV2AnnouncesRx                     PerfCounter64,
      f3PtpL3PTPPortHistoryV2AnnouncesTx                     PerfCounter64,
      f3PtpL3PTPPortHistoryV2SyncsRx                         PerfCounter64,
      f3PtpL3PTPPortHistoryV2SyncsTx                         PerfCounter64,
      f3PtpL3PTPPortHistoryV2FollowupsRx                     PerfCounter64,
      f3PtpL3PTPPortHistoryV2FollowupsTx                     PerfCounter64,
      f3PtpL3PTPPortHistoryV2DelayReqsRx                     PerfCounter64,
      f3PtpL3PTPPortHistoryV2DelayReqsTx                     PerfCounter64,
      f3PtpL3PTPPortHistoryV2DelayRspsRx                     PerfCounter64,
      f3PtpL3PTPPortHistoryV2DelayRspsTx                     PerfCounter64,
      f3PtpL3PTPPortHistoryV2SignalingRx                     PerfCounter64,
      f3PtpL3PTPPortHistoryV2SignalingTx                     PerfCounter64,
      f3PtpL3PTPPortHistoryV2MgmtFramesRx                    PerfCounter64,
      f3PtpL3PTPPortHistoryV2MgmtFramesTx                    PerfCounter64,
      f3PtpL3PTPPortHistoryV2PtpUnknownsRx                   PerfCounter64,
      f3PtpL3PTPPortHistoryV2AvgSyncResTime                  Unsigned32,
      f3PtpL3PTPPortHistoryV2MinSyncResTime                  Unsigned32,
      f3PtpL3PTPPortHistoryV2MaxSyncResTime                  Unsigned32,
      f3PtpL3PTPPortHistoryV2AvgDelayReqResTime              Unsigned32,
      f3PtpL3PTPPortHistoryV2MinDelayReqResTime              Unsigned32,
      f3PtpL3PTPPortHistoryV2MaxDelayReqResTime              Unsigned32,
      f3PtpL3PTPPortHistoryV2AvgAnnounceRate                 Unsigned32,
      f3PtpL3PTPPortHistoryV2AvgSyncRate                     Unsigned32,
      f3PtpL3PTPPortHistoryV2AvgDelayReqRate                 Unsigned32,
      f3PtpL3PTPPortHistoryV2AvgDelayRespRate                Unsigned32,
      f3PtpL3PTPPortHistoryV2MismatchDomainDiscards          PerfCounter64,
      f3PtpL3PTPPortHistoryV2MessageWrongTypeDiscards        PerfCounter64,
      f3PtpL3PTPPortHistoryV2MessagesWrongLengthDiscards     PerfCounter64,
      f3PtpL3PTPPortHistoryV2UnknownMasterDiscards           PerfCounter64,
      f3PtpL3PTPPortHistoryV2MessageMiscDiscards             PerfCounter64
    }

f3PtpL3PTPPortHistoryV2IntervalType OBJECT-TYPE
    SYNTAX      CmPmIntervalType 
    MAX-ACCESS  read-only
    STATUS      current
    DESCRIPTION
        "Interval Type of L3 PTP Port History Data."
    ::= { f3PtpL3PTPPortHistoryV2Entry 1 }

f3PtpL3PTPPortHistoryV2TimeStamp OBJECT-TYPE
    SYNTAX      DateAndTime 
    MAX-ACCESS  read-only
    STATUS      current
    DESCRIPTION
        "Time Stamp of L3 PTP Port History Data."
    ::= { f3PtpL3PTPPortHistoryV2Entry 2 }

f3PtpL3PTPPortHistoryV2ValidFlag OBJECT-TYPE
    SYNTAX      TruthValue 
    MAX-ACCESS  read-only
    STATUS      current
    DESCRIPTION
        "Valid Flag of L3 PTP Port History Data."
    ::= { f3PtpL3PTPPortHistoryV2Entry 3 }

f3PtpL3PTPPortHistoryV2Action OBJECT-TYPE
    SYNTAX      CmPmBinAction 
    MAX-ACCESS  read-write
    STATUS      current
    DESCRIPTION
        "Action of L3 PTP Port History Data."
    ::= { f3PtpL3PTPPortHistoryV2Entry 4 }

f3PtpL3PTPPortHistoryV2OutOfSequenceAnnouceMessages OBJECT-TYPE
    SYNTAX      PerfCounter64 
    MAX-ACCESS  read-only
    STATUS      current
    DESCRIPTION
        "Out of sequence Announce messages."
    ::= { f3PtpL3PTPPortHistoryV2Entry 5 }

f3PtpL3PTPPortHistoryV2OutOfSequenceSyncMessages OBJECT-TYPE
    SYNTAX      PerfCounter64 
    MAX-ACCESS  read-only
    STATUS      current
    DESCRIPTION
        "Out of sequence Sync messages."
    ::= { f3PtpL3PTPPortHistoryV2Entry 6 }

f3PtpL3PTPPortHistoryV2MgmtMessagesDiscards OBJECT-TYPE
    SYNTAX      PerfCounter64 
    MAX-ACCESS  read-only
    STATUS      current
    DESCRIPTION
        "Management messages discarded."
    ::= { f3PtpL3PTPPortHistoryV2Entry 7 }

f3PtpL3PTPPortHistoryV2AnnounceDeniedEventsTx OBJECT-TYPE
    SYNTAX      PerfCounter64 
    MAX-ACCESS  read-only
    STATUS      current
    DESCRIPTION
        "Announce Service Denied Events Transmitted."
    ::= { f3PtpL3PTPPortHistoryV2Entry 8 }

f3PtpL3PTPPortHistoryV2SyncDeniedEventsTx OBJECT-TYPE
    SYNTAX      PerfCounter64 
    MAX-ACCESS  read-only
    STATUS      current
    DESCRIPTION
        "Sync Service Denied Events Transmitted."
    ::= { f3PtpL3PTPPortHistoryV2Entry 9 }

f3PtpL3PTPPortHistoryV2DynamicSlavesLearnedCount OBJECT-TYPE
    SYNTAX      PerfCounter64 
    MAX-ACCESS  read-only
    STATUS      current
    DESCRIPTION
        "Dynamic Slaves Services Learned Count."
    ::= { f3PtpL3PTPPortHistoryV2Entry 10 }

f3PtpL3PTPPortHistoryV2DynamicSlavesDropped OBJECT-TYPE
    SYNTAX      PerfCounter64 
    MAX-ACCESS  read-only
    STATUS      current
    DESCRIPTION
        "Dynamic Slaves Service Dropped."
    ::= { f3PtpL3PTPPortHistoryV2Entry 11 }

f3PtpL3PTPPortHistoryV2DelayRespDeniedEventsTx OBJECT-TYPE
    SYNTAX      PerfCounter64 
    MAX-ACCESS  read-only
    STATUS      current
    DESCRIPTION
        "Delay Response Service Denied Events Transmitted."
    ::= { f3PtpL3PTPPortHistoryV2Entry 12 }

f3PtpL3PTPPortHistoryV2AnnounceCancelledEventsTx OBJECT-TYPE
    SYNTAX      PerfCounter64 
    MAX-ACCESS  read-only
    STATUS      current
    DESCRIPTION
        "Announce Service Cancelled Events Transmitted."
    ::= { f3PtpL3PTPPortHistoryV2Entry 13 }

f3PtpL3PTPPortHistoryV2SyncCancelledEventsTx OBJECT-TYPE
    SYNTAX      PerfCounter64 
    MAX-ACCESS  read-only
    STATUS      current
    DESCRIPTION
        "Sync Service Cancelled Events Transmitted."
    ::= { f3PtpL3PTPPortHistoryV2Entry 14 }

f3PtpL3PTPPortHistoryV2DelayRespCancelledEventsTx OBJECT-TYPE
    SYNTAX      PerfCounter64 
    MAX-ACCESS  read-only
    STATUS      current
    DESCRIPTION
        "Delay Response Service Cancelled Events Transmitted."
    ::= { f3PtpL3PTPPortHistoryV2Entry 15 }

f3PtpL3PTPPortHistoryV2AnnounceDeniedEventsRx OBJECT-TYPE
    SYNTAX      PerfCounter64 
    MAX-ACCESS  read-only
    STATUS      current
    DESCRIPTION
        "Announce Service Denied Events Received."
    ::= { f3PtpL3PTPPortHistoryV2Entry 16 }

f3PtpL3PTPPortHistoryV2SyncDeniedEventsRx OBJECT-TYPE
    SYNTAX      PerfCounter64 
    MAX-ACCESS  read-only
    STATUS      current
    DESCRIPTION
        "Sync Service Denied Events Received."
    ::= { f3PtpL3PTPPortHistoryV2Entry 17 }

f3PtpL3PTPPortHistoryV2DelayRespDeniedEventsRx OBJECT-TYPE
    SYNTAX      PerfCounter64 
    MAX-ACCESS  read-only
    STATUS      current
    DESCRIPTION
        "Delay Response Service Denied Events Received."
    ::= { f3PtpL3PTPPortHistoryV2Entry 18 }

f3PtpL3PTPPortHistoryV2AnnounceCancelledEventsRx OBJECT-TYPE
    SYNTAX      PerfCounter64 
    MAX-ACCESS  read-only
    STATUS      current
    DESCRIPTION
        "Announce Service Cancelled Events Received."
    ::= { f3PtpL3PTPPortHistoryV2Entry 19 }

f3PtpL3PTPPortHistoryV2SyncCancelledEventsRx OBJECT-TYPE
    SYNTAX      PerfCounter64 
    MAX-ACCESS  read-only
    STATUS      current
    DESCRIPTION
        "Sync Service Cancelled Events Received."
    ::= { f3PtpL3PTPPortHistoryV2Entry 20 }

f3PtpL3PTPPortHistoryV2DelayRespCancelledEventsRx OBJECT-TYPE
    SYNTAX      PerfCounter64 
    MAX-ACCESS  read-only
    STATUS      current
    DESCRIPTION
        "Delay Response Service Cancelled Events Received."
    ::= { f3PtpL3PTPPortHistoryV2Entry 21 }

f3PtpL3PTPPortHistoryV2AnnouncesRx OBJECT-TYPE
    SYNTAX      PerfCounter64 
    MAX-ACCESS  read-only
    STATUS      current
    DESCRIPTION
        "Announces Rx of L3 PTP Port History Data."
    ::= { f3PtpL3PTPPortHistoryV2Entry 22 }

f3PtpL3PTPPortHistoryV2AnnouncesTx OBJECT-TYPE
    SYNTAX      PerfCounter64 
    MAX-ACCESS  read-only
    STATUS      current
    DESCRIPTION
        "Announces Tx of L3 PTP Port History Data."
    ::= { f3PtpL3PTPPortHistoryV2Entry 23 }

f3PtpL3PTPPortHistoryV2SyncsRx OBJECT-TYPE
    SYNTAX      PerfCounter64 
    MAX-ACCESS  read-only
    STATUS      current
    DESCRIPTION
        "Syncs Rx of L3 PTP Port History Data."
    ::= { f3PtpL3PTPPortHistoryV2Entry 24 }

f3PtpL3PTPPortHistoryV2SyncsTx OBJECT-TYPE
    SYNTAX      PerfCounter64 
    MAX-ACCESS  read-only
    STATUS      current
    DESCRIPTION
        "Syncs Tx of L3 PTP Port History Data."
    ::= { f3PtpL3PTPPortHistoryV2Entry 25 }

f3PtpL3PTPPortHistoryV2FollowupsRx OBJECT-TYPE
    SYNTAX      PerfCounter64 
    MAX-ACCESS  read-only
    STATUS      current
    DESCRIPTION
        "Followups Rx of L3 PTP Port History Data."
    ::= { f3PtpL3PTPPortHistoryV2Entry 26 }

f3PtpL3PTPPortHistoryV2FollowupsTx OBJECT-TYPE
    SYNTAX      PerfCounter64 
    MAX-ACCESS  read-only
    STATUS      current
    DESCRIPTION
        "Followups Tx of L3 PTP Port History Data."
    ::= { f3PtpL3PTPPortHistoryV2Entry 27 }

f3PtpL3PTPPortHistoryV2DelayReqsRx OBJECT-TYPE
    SYNTAX      PerfCounter64 
    MAX-ACCESS  read-only
    STATUS      current
    DESCRIPTION
        "Delay Reqs Rx of L3 PTP Port History Data."
    ::= { f3PtpL3PTPPortHistoryV2Entry 28 }

f3PtpL3PTPPortHistoryV2DelayReqsTx OBJECT-TYPE
    SYNTAX      PerfCounter64 
    MAX-ACCESS  read-only
    STATUS      current
    DESCRIPTION
        "Delay Reqs Tx of L3 PTP Port History Data."
    ::= { f3PtpL3PTPPortHistoryV2Entry 29 }

f3PtpL3PTPPortHistoryV2DelayRspsRx OBJECT-TYPE
    SYNTAX      PerfCounter64 
    MAX-ACCESS  read-only
    STATUS      current
    DESCRIPTION
        "Delay Rsps Rx of L3 PTP Port History Data."
    ::= { f3PtpL3PTPPortHistoryV2Entry 30 }

f3PtpL3PTPPortHistoryV2DelayRspsTx OBJECT-TYPE
    SYNTAX      PerfCounter64 
    MAX-ACCESS  read-only
    STATUS      current
    DESCRIPTION
        "Delay Rsps Tx of L3 PTP Port History Data."
    ::= { f3PtpL3PTPPortHistoryV2Entry 31 }

f3PtpL3PTPPortHistoryV2SignalingRx OBJECT-TYPE
    SYNTAX      PerfCounter64 
    MAX-ACCESS  read-only
    STATUS      current
    DESCRIPTION
        "Signaling Rx of L3 PTP Port History Data."
    ::= { f3PtpL3PTPPortHistoryV2Entry 32 }

f3PtpL3PTPPortHistoryV2SignalingTx OBJECT-TYPE
    SYNTAX      PerfCounter64 
    MAX-ACCESS  read-only
    STATUS      current
    DESCRIPTION
        "Signaling Tx of L3 PTP Port History Data."
    ::= { f3PtpL3PTPPortHistoryV2Entry 33 }

f3PtpL3PTPPortHistoryV2MgmtFramesRx OBJECT-TYPE
    SYNTAX      PerfCounter64 
    MAX-ACCESS  read-only
    STATUS      current
    DESCRIPTION
        "Mgmt Frames Rx of L3 PTP Port History Data."
    ::= { f3PtpL3PTPPortHistoryV2Entry 34 }

f3PtpL3PTPPortHistoryV2MgmtFramesTx OBJECT-TYPE
    SYNTAX      PerfCounter64 
    MAX-ACCESS  read-only
    STATUS      current
    DESCRIPTION
        "Mgmt Frames Tx of L3 PTP Port History Data."
    ::= { f3PtpL3PTPPortHistoryV2Entry 35 }

f3PtpL3PTPPortHistoryV2PtpUnknownsRx OBJECT-TYPE
    SYNTAX      PerfCounter64 
    MAX-ACCESS  read-only
    STATUS      current
    DESCRIPTION
        "Ptp Unknowns Rx of L3 PTP Port History Data."
    ::= { f3PtpL3PTPPortHistoryV2Entry 36 }

f3PtpL3PTPPortHistoryV2AvgSyncResTime OBJECT-TYPE
    SYNTAX      Unsigned32 
    MAX-ACCESS  read-only
    STATUS      current
    DESCRIPTION
        "Avg Sync Res Time of L3 PTP Port History Data."
    ::= { f3PtpL3PTPPortHistoryV2Entry 37 }

f3PtpL3PTPPortHistoryV2MinSyncResTime OBJECT-TYPE
    SYNTAX      Unsigned32 
    MAX-ACCESS  read-only
    STATUS      current
    DESCRIPTION
        "Min Sync Res Time of L3 PTP Port History Data."
    ::= { f3PtpL3PTPPortHistoryV2Entry 38 }

f3PtpL3PTPPortHistoryV2MaxSyncResTime OBJECT-TYPE
    SYNTAX      Unsigned32 
    MAX-ACCESS  read-only
    STATUS      current
    DESCRIPTION
        "Max Sync Res Time of L3 PTP Port History Data."
    ::= { f3PtpL3PTPPortHistoryV2Entry 39 }

f3PtpL3PTPPortHistoryV2AvgDelayReqResTime OBJECT-TYPE
    SYNTAX      Unsigned32 
    MAX-ACCESS  read-only
    STATUS      current
    DESCRIPTION
        "Avg Delay Req Res Time of L3 PTP Port History Data."
    ::= { f3PtpL3PTPPortHistoryV2Entry 40 }

f3PtpL3PTPPortHistoryV2MinDelayReqResTime OBJECT-TYPE
    SYNTAX      Unsigned32 
    MAX-ACCESS  read-only
    STATUS      current
    DESCRIPTION
        "Min Delay Req Res Time of L3 PTP Port History Data."
    ::= { f3PtpL3PTPPortHistoryV2Entry 41 }

f3PtpL3PTPPortHistoryV2MaxDelayReqResTime OBJECT-TYPE
    SYNTAX      Unsigned32 
    MAX-ACCESS  read-only
    STATUS      current
    DESCRIPTION
        "Max Delay Req Res Time of L3 PTP Port History Data."
    ::= { f3PtpL3PTPPortHistoryV2Entry 42 }

f3PtpL3PTPPortHistoryV2AvgAnnounceRate OBJECT-TYPE
    SYNTAX      Unsigned32 
    MAX-ACCESS  read-only
    STATUS      current
    DESCRIPTION
        "Avg Announce Rate of L3 PTP Port History Data."
    ::= { f3PtpL3PTPPortHistoryV2Entry 43 }

f3PtpL3PTPPortHistoryV2AvgSyncRate OBJECT-TYPE
    SYNTAX      Unsigned32 
    MAX-ACCESS  read-only
    STATUS      current
    DESCRIPTION
        "Avg Sync Rate of L3 PTP Port History Data."
    ::= { f3PtpL3PTPPortHistoryV2Entry 44 }

f3PtpL3PTPPortHistoryV2AvgDelayReqRate OBJECT-TYPE
    SYNTAX      Unsigned32 
    MAX-ACCESS  read-only
    STATUS      current
    DESCRIPTION
        "Avg Delay Req Rate of L3 PTP Port History Data."
    ::= { f3PtpL3PTPPortHistoryV2Entry 45 }

f3PtpL3PTPPortHistoryV2AvgDelayRespRate OBJECT-TYPE
    SYNTAX      Unsigned32 
    MAX-ACCESS  read-only
    STATUS      current
    DESCRIPTION
        "Avg Delay Resp Rate of L3 PTP Port History Data."
    ::= { f3PtpL3PTPPortHistoryV2Entry 46 }

f3PtpL3PTPPortHistoryV2MismatchDomainDiscards OBJECT-TYPE
    SYNTAX      PerfCounter64 
    MAX-ACCESS  read-only
    STATUS      current
    DESCRIPTION
        "Mismatch Domain Discards of L3 PTP Port History Data."
    ::= { f3PtpL3PTPPortHistoryV2Entry 47 }

f3PtpL3PTPPortHistoryV2MessageWrongTypeDiscards OBJECT-TYPE
    SYNTAX      PerfCounter64 
    MAX-ACCESS  read-only
    STATUS      current
    DESCRIPTION
        "Message Wrong Type Discards of L3 PTP Port History Data."
    ::= { f3PtpL3PTPPortHistoryV2Entry 48 }

f3PtpL3PTPPortHistoryV2MessagesWrongLengthDiscards OBJECT-TYPE
    SYNTAX      PerfCounter64 
    MAX-ACCESS  read-only
    STATUS      current
    DESCRIPTION
        "Messages Wrong Length Discards of L3 PTP Port History Data."
    ::= { f3PtpL3PTPPortHistoryV2Entry 49 }

f3PtpL3PTPPortHistoryV2UnknownMasterDiscards OBJECT-TYPE
    SYNTAX      PerfCounter64 
    MAX-ACCESS  read-only
    STATUS      current
    DESCRIPTION
        "Unknown Master Discards of L3 PTP Port History Data."
    ::= { f3PtpL3PTPPortHistoryV2Entry 50 }

f3PtpL3PTPPortHistoryV2MessageMiscDiscards OBJECT-TYPE
    SYNTAX      PerfCounter64 
    MAX-ACCESS  read-only
    STATUS      current
    DESCRIPTION
        "Message Misc Discards of L3 PTP Port History Data."
    ::= { f3PtpL3PTPPortHistoryV2Entry 51 }

--
-- L3 Remote Slave Table      
--
f3PtpL3DynamicRemoteSlaveTable OBJECT-TYPE
    SYNTAX     SEQUENCE OF F3PtpL3DynamicRemoteSlaveEntry
    MAX-ACCESS not-accessible
    STATUS     current
    DESCRIPTION
       "A list of entries corresponding to the PTP Remote Slave entities."
    ::= { f3PtpConfigObjects 26 }

f3PtpL3DynamicRemoteSlaveEntry OBJECT-TYPE
    SYNTAX     F3PtpL3DynamicRemoteSlaveEntry
    MAX-ACCESS not-accessible
    STATUS     current
    DESCRIPTION
          "An entry containing information applicable to a particular
           Dynamic Remote Slave entity."
    INDEX { neIndex, f3PtpPTPClockIndex, f3PtpL3PTPPortIndex, f3PtpL3DynamicRemoteSlaveIndex}
            
    ::= { f3PtpL3DynamicRemoteSlaveTable 1 }

F3PtpL3DynamicRemoteSlaveEntry ::= SEQUENCE {
    f3PtpL3DynamicRemoteSlaveIndex                    Integer32,
    f3PtpL3DynamicRemoteSlaveAlias                    DisplayString,
    f3PtpL3DynamicRemoteSlaveAdminState               AdminState,
    f3PtpL3DynamicRemoteSlaveOperationalState         OperationalState,
    f3PtpL3DynamicRemoteSlaveSecondaryState           SecondaryState,
    f3PtpL3DynamicRemoteSlaveClockIdentity            ClockIdentity,
    f3PtpL3DynamicRemoteSlaveIpV4Address              IpAddress,
    f3PtpL3DynamicRemoteSlaveTimeCreated              DateAndTime,
    f3PtpL3DynamicRemoteSlaveSyncMsgRate              SyncMsgRate,
    f3PtpL3DynamicRemoteSlaveDelayRspMsgRate          DelayRespMsgRate,
    f3PtpL3DynamicRemoteSlaveAnnounceMsgRate          AnnounceMsgRate,
    f3PtpL3DynamicRemoteSlaveNegSyncLeaseDur          Integer32,
    f3PtpL3DynamicRemoteSlaveNegDelayRspLeaseDur      Integer32,
    f3PtpL3DynamicRemoteSlaveNegAnnounceLeaseDur      Integer32,
    f3PtpL3DynamicRemoteSlaveSyncDurRemTime           Unsigned32,
    f3PtpL3DynamicRemoteSlaveDelayRspDurRemTime       Unsigned32,
    f3PtpL3DynamicRemoteSlaveAnnounceDurRemTime       Unsigned32,
    f3PtpL3DynamicRemoteSlaveIpV6Address              Ipv6Address,
    f3PtpL3DynamicRemoteSlaveRowStatus                RowStatus,
    f3PtpL3DynamicRemoteSlaveStorageType              StorageType
}

f3PtpL3DynamicRemoteSlaveIndex OBJECT-TYPE
    SYNTAX     Integer32
    MAX-ACCESS not-accessible 
    STATUS     current
    DESCRIPTION
         "Unique index value associated with the Remote Slave."
     ::= { f3PtpL3DynamicRemoteSlaveEntry 1 }

f3PtpL3DynamicRemoteSlaveAlias    OBJECT-TYPE
    SYNTAX      DisplayString (SIZE(0..256))
    MAX-ACCESS  read-create
    STATUS      current
    DESCRIPTION
         "This object allows SNMP management entities to provide an 
          alias to the Remote Slave."
     ::= { f3PtpL3DynamicRemoteSlaveEntry 2 }

f3PtpL3DynamicRemoteSlaveAdminState OBJECT-TYPE
    SYNTAX      AdminState 
    MAX-ACCESS  read-create
    STATUS      current
    DESCRIPTION
          "This object represents the Administrative State of the Remote Slave."
    ::= { f3PtpL3DynamicRemoteSlaveEntry 3 }

f3PtpL3DynamicRemoteSlaveOperationalState   OBJECT-TYPE
    SYNTAX      OperationalState 
    MAX-ACCESS  read-only
    STATUS      current
    DESCRIPTION
          "This object represents the Operational State of the Remote Slave."
    ::= { f3PtpL3DynamicRemoteSlaveEntry 4 }

f3PtpL3DynamicRemoteSlaveSecondaryState     OBJECT-TYPE
    SYNTAX      SecondaryState 
    MAX-ACCESS  read-only
    STATUS      current
    DESCRIPTION
           "This object represents the Secondary State of the Remote Slave."
    ::= { f3PtpL3DynamicRemoteSlaveEntry 5 }

f3PtpL3DynamicRemoteSlaveClockIdentity OBJECT-TYPE
    SYNTAX     ClockIdentity 
    MAX-ACCESS read-only
    STATUS     current
    DESCRIPTION
         "This object represents the Clock Identity of the Remote Slave."
     ::= { f3PtpL3DynamicRemoteSlaveEntry 6 }

f3PtpL3DynamicRemoteSlaveIpV4Address OBJECT-TYPE
    SYNTAX     IpAddress
    MAX-ACCESS read-only 
    STATUS     current
    DESCRIPTION
         "This object allows specification of the IPv4 Address of
          the Remote Slave."
     ::= { f3PtpL3DynamicRemoteSlaveEntry 7 }

f3PtpL3DynamicRemoteSlaveTimeCreated OBJECT-TYPE
    SYNTAX     DateAndTime
    MAX-ACCESS read-only 
    STATUS     current
    DESCRIPTION
         "This object presents time when this Remote Slave entity was created."
     ::= { f3PtpL3DynamicRemoteSlaveEntry 8 }

f3PtpL3DynamicRemoteSlaveSyncMsgRate OBJECT-TYPE
    SYNTAX     SyncMsgRate
    MAX-ACCESS read-only
    STATUS     current
    DESCRIPTION
         "This attribute specifies Sync Message Rate of the Remote Slave."
     ::= { f3PtpL3DynamicRemoteSlaveEntry 9 }

f3PtpL3DynamicRemoteSlaveDelayRspMsgRate OBJECT-TYPE
    SYNTAX     DelayRespMsgRate
    MAX-ACCESS read-only
    STATUS     current
    DESCRIPTION
         "This attribute specifies Delay Respone Message Rate of the Remote Slave."
     ::= { f3PtpL3DynamicRemoteSlaveEntry 10 }

f3PtpL3DynamicRemoteSlaveAnnounceMsgRate OBJECT-TYPE
    SYNTAX     AnnounceMsgRate
    MAX-ACCESS read-only
    STATUS     current
    DESCRIPTION
         "This attribute specifies Announce Message Rate of the Remote Slave."
     ::= { f3PtpL3DynamicRemoteSlaveEntry 11 }

f3PtpL3DynamicRemoteSlaveNegSyncLeaseDur OBJECT-TYPE
    SYNTAX     Integer32
    MAX-ACCESS read-only
    STATUS     current
    DESCRIPTION
         "This attribute indicates Sync messages negotiated Lease Duration in seconds."
     ::= { f3PtpL3DynamicRemoteSlaveEntry 12 }

f3PtpL3DynamicRemoteSlaveNegDelayRspLeaseDur OBJECT-TYPE
    SYNTAX     Integer32
    MAX-ACCESS read-only
    STATUS     current
    DESCRIPTION
         "This attribute indicates Delay Response messages negotiated Lease 
          Duration in seconds."
     ::= { f3PtpL3DynamicRemoteSlaveEntry 13 }

f3PtpL3DynamicRemoteSlaveNegAnnounceLeaseDur OBJECT-TYPE
    SYNTAX     Integer32
    MAX-ACCESS read-only
    STATUS     current
    DESCRIPTION
         "This attribute indicates Announce messages negotiated Lease 
          Duration in seconds."
     ::= { f3PtpL3DynamicRemoteSlaveEntry 14 }

f3PtpL3DynamicRemoteSlaveSyncDurRemTime OBJECT-TYPE
    SYNTAX     Unsigned32
    MAX-ACCESS read-only
    STATUS     current
    DESCRIPTION
         "This attribute indicates Remaining seconds of Lease Duration of Sync service."
     ::= { f3PtpL3DynamicRemoteSlaveEntry 15 }

f3PtpL3DynamicRemoteSlaveDelayRspDurRemTime OBJECT-TYPE
    SYNTAX     Unsigned32
    MAX-ACCESS read-only
    STATUS     current
    DESCRIPTION
         "This attribute indicates Remaining seconds of Lease Duration of Delay Response 
          service."
     ::= { f3PtpL3DynamicRemoteSlaveEntry 16 }

f3PtpL3DynamicRemoteSlaveAnnounceDurRemTime OBJECT-TYPE
    SYNTAX     Unsigned32
    MAX-ACCESS read-only
    STATUS     current
    DESCRIPTION
         "This attribute indicates Remaining seconds of Lease Duration of Announce 
          service."
     ::= { f3PtpL3DynamicRemoteSlaveEntry 17 }

f3PtpL3DynamicRemoteSlaveIpV6Address OBJECT-TYPE
    SYNTAX     Ipv6Address 
    MAX-ACCESS read-only
    STATUS   current
    DESCRIPTION
         "This object allows specification of the unicast IPv6 Address of
          the Remote Slave."
    ::= { f3PtpL3DynamicRemoteSlaveEntry 18 }
    

f3PtpL3DynamicRemoteSlaveRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpL3DynamicRemoteSlaveRowStatus supported is
            destroy(6).  

            The f3PtpL3DynamicRemoteSlaveRowStatus object may be modified if
            the associated instance of this object is equal to active(1)."
    ::= { f3PtpL3DynamicRemoteSlaveEntry 19 }


f3PtpL3DynamicRemoteSlaveStorageType OBJECT-TYPE
    SYNTAX     StorageType
    MAX-ACCESS read-create
    STATUS     current
    DESCRIPTION
            "The type of storage configured for this entry."
    ::= { f3PtpL3DynamicRemoteSlaveEntry 20 }

--
-- Ptp L3 Remote Slave current data
--
f3PtpL3RemoteSlaveStatsTable OBJECT-TYPE
    SYNTAX      SEQUENCE OF F3PtpL3RemoteSlaveStatsEntry
    MAX-ACCESS  not-accessible
    STATUS      current
    DESCRIPTION
            "A collection of Remote Slave related statistics.  
             These reflect the current data."
    ::= { f3PtpPerformanceObjects 33 }

f3PtpL3RemoteSlaveStatsEntry OBJECT-TYPE
    SYNTAX      F3PtpL3RemoteSlaveStatsEntry 
    MAX-ACCESS  not-accessible
    STATUS      current
    DESCRIPTION
            "A conceptual row in the f3PtpL3RemoteSlaveStatsTable.
             Entries exist in this table for each Remote Slave."
    INDEX { neIndex, f3PtpPTPClockIndex, f3PtpL3PTPPortIndex, f3PtpL3DynamicRemoteSlaveIndex, f3PtpL3RemoteSlaveStatsIndex}
    ::= { f3PtpL3RemoteSlaveStatsTable 1 }

F3PtpL3RemoteSlaveStatsEntry ::= SEQUENCE {
    f3PtpL3RemoteSlaveStatsIndex                    Integer32,
    f3PtpL3RemoteSlaveStatsIntervalType             CmPmIntervalType,
    f3PtpL3RemoteSlaveStatsValid                    TruthValue,
    f3PtpL3RemoteSlaveStatsAction                   CmPmBinAction,
    f3PtpL3RemoteSlaveStatsSyncMsgsGen              PerfCounter64,
    f3PtpL3RemoteSlaveStatsDelayRspMsgsGen          PerfCounter64,
    f3PtpL3RemoteSlaveStatsAnnounceMsgsGen          PerfCounter64,
    f3PtpL3RemoteSlaveStatsSignallingMsgsGen        PerfCounter64,
    f3PtpL3RemoteSlaveStatsDelayReqMsgsRx           PerfCounter64,
    f3PtpL3RemoteSlaveStatsSignallingMsgsRx         PerfCounter64,
    f3PtpL3RemoteSlaveStatsDelayReqMsgsDropped      PerfCounter64,
    f3PtpL3RemoteSlaveStatsInvalidTLVLenDiscards    PerfCounter64,
    f3PtpL3RemoteSlaveStatsInvalidTLVTypeDiscards   PerfCounter64,
    f3PtpL3RemoteSlaveStatsTimesSyncLeaseExp        PerfCounter64,
    f3PtpL3RemoteSlaveStatsTimesDelayRspLeaseExp    PerfCounter64,
    f3PtpL3RemoteSlaveStatsTimesAnnounceLeaseExp    PerfCounter64
}

f3PtpL3RemoteSlaveStatsIndex OBJECT-TYPE
    SYNTAX      Integer32 (1..4)
    MAX-ACCESS  not-accessible
    STATUS      current
    DESCRIPTION
            "An arbitrary integer index value used to uniquely identify
            this Remote Slave statistics entry. 
            1 - 15min
            2 - 1day
            3 - rollover
            4 - 5min"
    ::= { f3PtpL3RemoteSlaveStatsEntry 1 }

f3PtpL3RemoteSlaveStatsIntervalType OBJECT-TYPE
    SYNTAX      CmPmIntervalType
    MAX-ACCESS  read-only
    STATUS      current
    DESCRIPTION
            "Indicates the type of collection, i.e. whether it is
             15 Min, 1 Day or rollover."
    ::= { f3PtpL3RemoteSlaveStatsEntry 2 }

f3PtpL3RemoteSlaveStatsValid OBJECT-TYPE
    SYNTAX      TruthValue
    MAX-ACCESS  read-only
    STATUS      current
    DESCRIPTION
            "Indicates the validity of the bin."
    ::= { f3PtpL3RemoteSlaveStatsEntry 3 }

f3PtpL3RemoteSlaveStatsAction OBJECT-TYPE
    SYNTAX      CmPmBinAction
    MAX-ACCESS  read-write
    STATUS      current
    DESCRIPTION
            "Allows the Manager to clear the bin."
    ::= { f3PtpL3RemoteSlaveStatsEntry 4 }

f3PtpL3RemoteSlaveStatsSyncMsgsGen OBJECT-TYPE
    SYNTAX      PerfCounter64
    MAX-ACCESS  read-only
    STATUS      current
    DESCRIPTION
            "Total Sync messages generated."
    ::= { f3PtpL3RemoteSlaveStatsEntry 5 }

f3PtpL3RemoteSlaveStatsDelayRspMsgsGen OBJECT-TYPE
    SYNTAX      PerfCounter64
    MAX-ACCESS  read-only
    STATUS      current
    DESCRIPTION
            "Total Delay Response messages generated."
    ::= { f3PtpL3RemoteSlaveStatsEntry 6 }

f3PtpL3RemoteSlaveStatsAnnounceMsgsGen OBJECT-TYPE
    SYNTAX      PerfCounter64
    MAX-ACCESS  read-only
    STATUS      current
    DESCRIPTION
            "Total Announce messages generated."
    ::= { f3PtpL3RemoteSlaveStatsEntry 7 }

f3PtpL3RemoteSlaveStatsSignallingMsgsGen OBJECT-TYPE
    SYNTAX      PerfCounter64
    MAX-ACCESS  read-only
    STATUS      current
    DESCRIPTION
            "Total Signalling messages generated."
    ::= { f3PtpL3RemoteSlaveStatsEntry 8 }

f3PtpL3RemoteSlaveStatsDelayReqMsgsRx OBJECT-TYPE
    SYNTAX      PerfCounter64
    MAX-ACCESS  read-only
    STATUS      current
    DESCRIPTION
            "Total Delay Request messages received."
    ::= { f3PtpL3RemoteSlaveStatsEntry 9 }

f3PtpL3RemoteSlaveStatsSignallingMsgsRx OBJECT-TYPE
    SYNTAX      PerfCounter64
    MAX-ACCESS  read-only
    STATUS      current
    DESCRIPTION
            "Total Signalling messages received."
    ::= { f3PtpL3RemoteSlaveStatsEntry 10 }

f3PtpL3RemoteSlaveStatsDelayReqMsgsDropped OBJECT-TYPE
    SYNTAX      PerfCounter64
    MAX-ACCESS  read-only
    STATUS      current
    DESCRIPTION
            "Total Delay Request messages dropped."
    ::= { f3PtpL3RemoteSlaveStatsEntry 11 }

f3PtpL3RemoteSlaveStatsInvalidTLVLenDiscards OBJECT-TYPE
    SYNTAX      PerfCounter64
    MAX-ACCESS  read-only
    STATUS      current
    DESCRIPTION
            "Total number of PTP messages discarded due to invalid PTP TLV length."
    ::= { f3PtpL3RemoteSlaveStatsEntry 12 }

f3PtpL3RemoteSlaveStatsInvalidTLVTypeDiscards OBJECT-TYPE
    SYNTAX      PerfCounter64
    MAX-ACCESS  read-only
    STATUS      current
    DESCRIPTION
            "Total number of PTP messages discarded due to invalid PTP TLV type."
    ::= { f3PtpL3RemoteSlaveStatsEntry 13 }

f3PtpL3RemoteSlaveStatsTimesSyncLeaseExp OBJECT-TYPE
    SYNTAX      PerfCounter64
    MAX-ACCESS  read-only
    STATUS      current
    DESCRIPTION
            "Count of Sync service lease duration expired events."
    ::= { f3PtpL3RemoteSlaveStatsEntry 14 }

f3PtpL3RemoteSlaveStatsTimesDelayRspLeaseExp OBJECT-TYPE
    SYNTAX      PerfCounter64
    MAX-ACCESS  read-only
    STATUS      current
    DESCRIPTION
            "Count of Delay Response service lease duration expired events."
    ::= { f3PtpL3RemoteSlaveStatsEntry 15 }

f3PtpL3RemoteSlaveStatsTimesAnnounceLeaseExp OBJECT-TYPE
    SYNTAX      PerfCounter64
    MAX-ACCESS  read-only
    STATUS      current
    DESCRIPTION
            "Count of Announce service lease duration expired events."
    ::= { f3PtpL3RemoteSlaveStatsEntry 16 }

--
-- Ptp L3 Remote Slave history data
--
f3PtpL3RemoteSlaveHistoryTable OBJECT-TYPE
    SYNTAX      SEQUENCE OF F3PtpL3RemoteSlaveHistoryEntry
    MAX-ACCESS  not-accessible
    STATUS      current
    DESCRIPTION
            "A collection of Remote Slave related history.  
             These reflect the current data."
    ::= { f3PtpPerformanceObjects 34 }

f3PtpL3RemoteSlaveHistoryEntry OBJECT-TYPE
    SYNTAX      F3PtpL3RemoteSlaveHistoryEntry 
    MAX-ACCESS  not-accessible
    STATUS      current
    DESCRIPTION
            "A conceptual row in the f3PtpL3RemoteSlaveHistoryTable.
             Entries exist in this table for each Remote Slave."
                 
    INDEX { neIndex, f3PtpPTPClockIndex, f3PtpL3PTPPortIndex, f3PtpL3DynamicRemoteSlaveIndex, f3PtpL3RemoteSlaveStatsIndex, 
    f3PtpL3RemoteSlaveHistoryIndex }
    ::= { f3PtpL3RemoteSlaveHistoryTable 1 }

F3PtpL3RemoteSlaveHistoryEntry ::= SEQUENCE {
    f3PtpL3RemoteSlaveHistoryIndex                    Integer32,
    f3PtpL3RemoteSlaveHistoryIntervalType             CmPmIntervalType,
    f3PtpL3RemoteSlaveHistoryTime                     DateAndTime,
    f3PtpL3RemoteSlaveHistoryValid                    TruthValue,
    f3PtpL3RemoteSlaveHistoryAction                   CmPmBinAction,
    f3PtpL3RemoteSlaveHistorySyncMsgsGen              PerfCounter64,
    f3PtpL3RemoteSlaveHistoryDelayRspMsgsGen          PerfCounter64,
    f3PtpL3RemoteSlaveHistoryAnnounceMsgsGen          PerfCounter64,
    f3PtpL3RemoteSlaveHistorySignallingMsgsGen        PerfCounter64,
    f3PtpL3RemoteSlaveHistoryDelayReqMsgsRx           PerfCounter64,
    f3PtpL3RemoteSlaveHistorySignallingMsgsRx         PerfCounter64,
    f3PtpL3RemoteSlaveHistoryDelayReqMsgsDropped      PerfCounter64,
    f3PtpL3RemoteSlaveHistoryInvalidTLVLenDiscards    PerfCounter64,
    f3PtpL3RemoteSlaveHistoryInvalidTLVTypeDiscards   PerfCounter64,
    f3PtpL3RemoteSlaveHistoryTimesSyncLeaseExp        PerfCounter64,
    f3PtpL3RemoteSlaveHistoryTimesDelayRspLeaseExp    PerfCounter64,
    f3PtpL3RemoteSlaveHistoryTimesAnnounceLeaseExp    PerfCounter64
}


f3PtpL3RemoteSlaveHistoryIndex OBJECT-TYPE
    SYNTAX      Integer32 (1..32)
    MAX-ACCESS  not-accessible
    STATUS      current
    DESCRIPTION
            "An arbitrary integer index value used to uniquely identify
             this Remote Slave PM history entry."
    ::= { f3PtpL3RemoteSlaveHistoryEntry 1 }


f3PtpL3RemoteSlaveHistoryIntervalType OBJECT-TYPE
    SYNTAX      CmPmIntervalType
    MAX-ACCESS  read-only
    STATUS      current
    DESCRIPTION
            "Indicates the type of collection, i.e. whether it is
             15 Min, 1 Day."
    ::= { f3PtpL3RemoteSlaveHistoryEntry 2 }
    
f3PtpL3RemoteSlaveHistoryTime OBJECT-TYPE
    SYNTAX      DateAndTime 
    MAX-ACCESS  read-only
    STATUS      current
    DESCRIPTION
            "Indicates the time of history bin creation." 
    ::= { f3PtpL3RemoteSlaveHistoryEntry 3 }

f3PtpL3RemoteSlaveHistoryValid OBJECT-TYPE
    SYNTAX      TruthValue
    MAX-ACCESS  read-only
    STATUS      current
    DESCRIPTION
            "Indicates the validity of the bin."
    ::= { f3PtpL3RemoteSlaveHistoryEntry 4 }

f3PtpL3RemoteSlaveHistoryAction OBJECT-TYPE
    SYNTAX      CmPmBinAction
    MAX-ACCESS  read-write
    STATUS      current
    DESCRIPTION
            "Allows the Manager to clear the bin."
    ::= { f3PtpL3RemoteSlaveHistoryEntry 5 }

f3PtpL3RemoteSlaveHistorySyncMsgsGen OBJECT-TYPE
    SYNTAX      PerfCounter64
    MAX-ACCESS  read-only
    STATUS      current
    DESCRIPTION
            "Total Sync messages generated."
    ::= { f3PtpL3RemoteSlaveHistoryEntry 6 }

f3PtpL3RemoteSlaveHistoryDelayRspMsgsGen OBJECT-TYPE
    SYNTAX      PerfCounter64
    MAX-ACCESS  read-only
    STATUS      current
    DESCRIPTION
            "Total Delay Response messages generated."
    ::= { f3PtpL3RemoteSlaveHistoryEntry 7 }

f3PtpL3RemoteSlaveHistoryAnnounceMsgsGen OBJECT-TYPE
    SYNTAX      PerfCounter64
    MAX-ACCESS  read-only
    STATUS      current
    DESCRIPTION
            "Total Announce messages generated."
    ::= { f3PtpL3RemoteSlaveHistoryEntry 8 }

f3PtpL3RemoteSlaveHistorySignallingMsgsGen OBJECT-TYPE
    SYNTAX      PerfCounter64
    MAX-ACCESS  read-only
    STATUS      current
    DESCRIPTION
            "Total Signalling messages generated."
    ::= { f3PtpL3RemoteSlaveHistoryEntry 9 }

f3PtpL3RemoteSlaveHistoryDelayReqMsgsRx OBJECT-TYPE
    SYNTAX      PerfCounter64
    MAX-ACCESS  read-only
    STATUS      current
    DESCRIPTION
            "Total Delay Request messages received."
    ::= { f3PtpL3RemoteSlaveHistoryEntry 10 }

f3PtpL3RemoteSlaveHistorySignallingMsgsRx OBJECT-TYPE
    SYNTAX      PerfCounter64
    MAX-ACCESS  read-only
    STATUS      current
    DESCRIPTION
            "Total Signalling messages received."
    ::= { f3PtpL3RemoteSlaveHistoryEntry 11 }

f3PtpL3RemoteSlaveHistoryDelayReqMsgsDropped OBJECT-TYPE
    SYNTAX      PerfCounter64
    MAX-ACCESS  read-only
    STATUS      current
    DESCRIPTION
            "Total Delay Request messages dropped."
    ::= { f3PtpL3RemoteSlaveHistoryEntry 12 }

f3PtpL3RemoteSlaveHistoryInvalidTLVLenDiscards OBJECT-TYPE
    SYNTAX      PerfCounter64
    MAX-ACCESS  read-only
    STATUS      current
    DESCRIPTION
            "Total number of PTP messages discarded due to invalid PTP TLV length."
    ::= { f3PtpL3RemoteSlaveHistoryEntry 13 }

f3PtpL3RemoteSlaveHistoryInvalidTLVTypeDiscards OBJECT-TYPE
    SYNTAX      PerfCounter64
    MAX-ACCESS  read-only
    STATUS      current
    DESCRIPTION
            "Total number of PTP messages discarded due to invalid PTP TLV type."
    ::= { f3PtpL3RemoteSlaveHistoryEntry 14 }

f3PtpL3RemoteSlaveHistoryTimesSyncLeaseExp OBJECT-TYPE
    SYNTAX      PerfCounter64
    MAX-ACCESS  read-only
    STATUS      current
    DESCRIPTION
            "Count of Sync service lease duration expired events."
    ::= { f3PtpL3RemoteSlaveHistoryEntry 15 }

f3PtpL3RemoteSlaveHistoryTimesDelayRspLeaseExp OBJECT-TYPE
    SYNTAX      PerfCounter64
    MAX-ACCESS  read-only
    STATUS      current
    DESCRIPTION
            "Count of Delay Response service lease duration expired events."
    ::= { f3PtpL3RemoteSlaveHistoryEntry 16 }

f3PtpL3RemoteSlaveHistoryTimesAnnounceLeaseExp OBJECT-TYPE
    SYNTAX      PerfCounter64
    MAX-ACCESS  read-only
    STATUS      current
    DESCRIPTION
            "Count of Announce service lease duration expired events."
    ::= { f3PtpL3RemoteSlaveHistoryEntry 17 }

--
-- Ptp L3 Remote Slave Threshold Table
--
f3PtpL3RemoteSlaveThresholdTable OBJECT-TYPE
    SYNTAX      SEQUENCE OF F3PtpL3RemoteSlaveThresholdEntry
    MAX-ACCESS  not-accessible
    STATUS      current
    DESCRIPTION
            "A table of entries that allow manageability of 
             Master Clock Interface Thresholds."
    ::= { f3PtpPerformanceObjects 35 }

f3PtpL3RemoteSlaveThresholdEntry OBJECT-TYPE
    SYNTAX      F3PtpL3RemoteSlaveThresholdEntry
    MAX-ACCESS  not-accessible
    STATUS      current
    DESCRIPTION
            "A conceptual row in the f3PtpL3RemoteSlaveThresholdTable."
    INDEX { neIndex, f3PtpPTPClockIndex, f3PtpL3PTPPortIndex, f3PtpL3DynamicRemoteSlaveIndex, 
            f3PtpL3RemoteSlaveStatsIndex, f3PtpL3RemoteSlaveThresholdIndex }
    ::= { f3PtpL3RemoteSlaveThresholdTable 1 }

F3PtpL3RemoteSlaveThresholdEntry ::= SEQUENCE {
    f3PtpL3RemoteSlaveThresholdIndex       Integer32,
    f3PtpL3RemoteSlaveThresholdInterval    CmPmIntervalType,
    f3PtpL3RemoteSlaveThresholdVariable    VariablePointer,
    f3PtpL3RemoteSlaveThresholdValueLo     Unsigned32,
    f3PtpL3RemoteSlaveThresholdValueHi     Unsigned32,
    f3PtpL3RemoteSlaveThresholdMonValue    PerfCounter64
}

f3PtpL3RemoteSlaveThresholdIndex OBJECT-TYPE
    SYNTAX     Integer32 (1..65535)
    MAX-ACCESS not-accessible
    STATUS     current
    DESCRIPTION
        "An index that uniquely identifies an entry in the
        f3PtpL3RemoteSlaveThresholdTable."
    ::= { f3PtpL3RemoteSlaveThresholdEntry 1 }

f3PtpL3RemoteSlaveThresholdInterval OBJECT-TYPE
    SYNTAX     CmPmIntervalType
    MAX-ACCESS read-only
    STATUS     current
    DESCRIPTION
        "The interval over which monitored value is
        sampled and compared with the specified threshold."
    ::= { f3PtpL3RemoteSlaveThresholdEntry 2 }

f3PtpL3RemoteSlaveThresholdVariable OBJECT-TYPE
    SYNTAX     VariablePointer
    MAX-ACCESS read-only
    STATUS     current
    DESCRIPTION
        "The object identifier of the particular variable to be
        sampled."
    ::= { f3PtpL3RemoteSlaveThresholdEntry 3 }

f3PtpL3RemoteSlaveThresholdValueLo OBJECT-TYPE
    SYNTAX     Unsigned32
    MAX-ACCESS read-write
    STATUS     current
    DESCRIPTION
        "Lower 32 bits of the threshold value."
    ::= { f3PtpL3RemoteSlaveThresholdEntry 4 }

f3PtpL3RemoteSlaveThresholdValueHi OBJECT-TYPE
    SYNTAX     Unsigned32
    MAX-ACCESS read-write
    STATUS     current
    DESCRIPTION
        "Higher 32 bits of the threshold value."
    ::= { f3PtpL3RemoteSlaveThresholdEntry 5 }

f3PtpL3RemoteSlaveThresholdMonValue OBJECT-TYPE
    SYNTAX     PerfCounter64
    MAX-ACCESS read-only
    STATUS     current
    DESCRIPTION
        "Monitored value corresponding to f3PtpL3RemoteSlaveThresholdVariable."
    ::= { f3PtpL3RemoteSlaveThresholdEntry 6 }

---
---Notifications
---
f3PtpAccPortFlowPointThresholdCrossingAlert NOTIFICATION-TYPE
    OBJECTS {
        f3PtpAccPortFlowPointThresholdIndex,
        f3PtpAccPortFlowPointThresholdInterval,
        f3PtpAccPortFlowPointThresholdVariable,
        f3PtpAccPortFlowPointThresholdValueLo,
        f3PtpAccPortFlowPointThresholdValueHi,
        f3PtpAccPortFlowPointThresholdMonValue
    }
    STATUS  current
    DESCRIPTION
            "This trap is sent each time a threshold on a PM condition
             on an PTP Access Port Flow Point is crossed."
  ::= { f3PtpPerformanceNotifications 1 }

f3PtpNetPortFlowPointThresholdCrossingAlert NOTIFICATION-TYPE
    OBJECTS {
        f3PtpNetPortFlowPointThresholdIndex,
        f3PtpNetPortFlowPointThresholdInterval,
        f3PtpNetPortFlowPointThresholdVariable,
        f3PtpNetPortFlowPointThresholdValueLo,
        f3PtpNetPortFlowPointThresholdValueHi,
        f3PtpNetPortFlowPointThresholdMonValue
    }
    STATUS  current
    DESCRIPTION
            "This trap is sent each time a threshold on a PM condition
             on an PTP Network Port Flow Point is crossed."
  ::= { f3PtpPerformanceNotifications 2 }


f3PtpSOOCCrossingAlert NOTIFICATION-TYPE
    OBJECTS {
        f3PtpSOOCThresholdIndex,
        f3PtpSOOCThresholdInterval,
        f3PtpSOOCThresholdVariable,
        f3PtpSOOCThresholdValueLo,
        f3PtpSOOCThresholdValueHi,
        f3PtpSOOCThresholdMonValue
    }
    STATUS  current
    DESCRIPTION
            "This trap is sent each time a threshold on a PM condition
             on an PTP Slave Only Ordinary Clock is crossed."
  ::= { f3PtpPerformanceNotifications 3 }

f3PtpTSCrossingAlert NOTIFICATION-TYPE
    OBJECTS {
        f3PtpTSThresholdIndex,
        f3PtpTSThresholdInterval,
        f3PtpTSThresholdVariable,
        f3PtpTSThresholdValueLo,
        f3PtpTSThresholdValueHi,
        f3PtpTSThresholdMonValue
    }
    STATUS  current
    DESCRIPTION
            "This trap is sent each time a threshold on a PM condition
             on an PTP Telecom Slave is crossed."
  ::= { f3PtpPerformanceNotifications 4 }


f3PtpMCICrossingAlert NOTIFICATION-TYPE
    OBJECTS {
        f3PtpMCIThresholdIndex,
        f3PtpMCIThresholdInterval,
        f3PtpMCIThresholdVariable,
        f3PtpMCIThresholdValueLo,
        f3PtpMCIThresholdValueHi,
        f3PtpMCIThresholdMonValue
    }
    STATUS  current
    DESCRIPTION
            "This trap is sent each time a threshold on a PM condition
             on an PTP Master Clock Interface is crossed."
  ::= { f3PtpPerformanceNotifications 5 }

f3PtpRemoteSlaveCrossingAlert NOTIFICATION-TYPE
    OBJECTS {
        f3PtpRemoteSlaveThresholdIndex,
        f3PtpRemoteSlaveThresholdInterval,
        f3PtpRemoteSlaveThresholdVariable,
        f3PtpRemoteSlaveThresholdValueLo,
        f3PtpRemoteSlaveThresholdValueHi,
        f3PtpRemoteSlaveThresholdMonValue
    }
    STATUS  current
    DESCRIPTION
            "This trap is sent each time a threshold on a PM condition
             on an PTP Remote Slave is crossed."
  ::= { f3PtpPerformanceNotifications 6 }

f3PtpTrafficPortFlowPointThresholdCrossingAlert NOTIFICATION-TYPE
    OBJECTS {
        f3PtpTrafficPortFlowPointThresholdIndex,
        f3PtpTrafficPortFlowPointThresholdInterval,
        f3PtpTrafficPortFlowPointThresholdVariable,
        f3PtpTrafficPortFlowPointThresholdValueLo,
        f3PtpTrafficPortFlowPointThresholdValueHi,
        f3PtpTrafficPortFlowPointThresholdMonValue
    }
    STATUS  current
    DESCRIPTION
            "This trap is sent each time a threshold on a PM condition
             on an PTP Traffic Port Flow Point is crossed."
  ::= { f3PtpPerformanceNotifications 7 }


--f3PtpPTPClockCrossingAlert NOTIFICATION-TYPE
--    OBJECTS {
--        f3PtpPTPClockThresholdIndex,
--        f3PtpPTPClockThresholdInterval,
--        f3PtpPTPClockThresholdVariable,
--        f3PtpPTPClockThresholdValueLo,
--        f3PtpPTPClockThresholdValueHi,
--        f3PtpPTPClockThresholdMonValue
--    }
--    STATUS  current
--    DESCRIPTION
--            "This trap is sent each time a threshold on a PM condition
--             on an PTP PTPClock is crossed."
--  ::= { f3PtpPerformanceNotifications 8 }

f3PtpPTPPortCrossingAlert NOTIFICATION-TYPE
    OBJECTS {
        f3PtpPTPPortThresholdIndex,
        f3PtpPTPPortThresholdInterval,
        f3PtpPTPPortThresholdVariable,
        f3PtpPTPPortThresholdValueLo,
        f3PtpPTPPortThresholdValueHi,
        f3PtpPTPPortThresholdMonValue
    }
    STATUS  current
    DESCRIPTION
            "This trap is sent each time a threshold on a PM condition
             on an PTP PTPPort is crossed."
  ::= { f3PtpPerformanceNotifications 8 }


f3PtpPTPClockCrossingAlert NOTIFICATION-TYPE
    OBJECTS {
        f3PtpPTPClockThresholdIndex,
        f3PtpPTPClockThresholdInterval,
        f3PtpPTPClockThresholdVariable,
        f3PtpPTPClockThresholdValueLo,
        f3PtpPTPClockThresholdValueHi,
        f3PtpPTPClockThresholdMonValue
    }
    STATUS  current
    DESCRIPTION
            "This trap is sent each time a threshold on a PM condition
             on an PTP PTPClock is crossed."
  ::= { f3PtpPerformanceNotifications 9 }


f3PtpL3PTPPortCrossingAlert NOTIFICATION-TYPE
    OBJECTS {
        f3PtpL3PTPPortThresholdIndex,
        f3PtpL3PTPPortThresholdInterval,
        f3PtpL3PTPPortThresholdVariable,
        f3PtpL3PTPPortThresholdValueLo,
        f3PtpL3PTPPortThresholdValueHi,
        f3PtpL3PTPPortThresholdMonValue
    }
    STATUS  current
    DESCRIPTION
            "This trap is sent each time a threshold on a PM condition
             on an L3 PTP Port is crossed."
  ::= { f3PtpPerformanceNotifications 10 }


f3PtpL3RemoteSlaveCrossingAlert NOTIFICATION-TYPE
    OBJECTS {
        f3PtpL3RemoteSlaveThresholdIndex,
        f3PtpL3RemoteSlaveThresholdInterval,
        f3PtpL3RemoteSlaveThresholdVariable,
        f3PtpL3RemoteSlaveThresholdValueLo,
        f3PtpL3RemoteSlaveThresholdValueHi,
        f3PtpL3RemoteSlaveThresholdMonValue
    }
    STATUS  current
    DESCRIPTION
            "This trap is sent each time a threshold on a PM condition
             on an PTP Remote Slave is crossed."
  ::= { f3PtpPerformanceNotifications 11 }


f3PtpTSStatusChangeTrap NOTIFICATION-TYPE
    OBJECTS {
        f3PtpTSAdminState,
        f3PtpTSCurrentCRScore,
        f3PtpTSCurrentPRScore,
        f3PtpTSClockRecoveryState,
        f3PtpTSSelectedPacketClock
    }
    STATUS  current
    DESCRIPTION
            "This trap is sent there is a status change on the Telecom Slave." 
  ::= { f3PtpStatusChangeNotifications 1 }


f3PtpMasterClockStatusChangeTrap NOTIFICATION-TYPE
    OBJECTS {
        f3PtpMasterClockClockClass,
        f3PtpMasterClockUtcOffset,
        f3PtpMasterClockActiveTimeRef,
        f3PtpMasterClockPTPProfile
    }
    STATUS  current
    DESCRIPTION
            "This trap is sent there is a status change on the Master Clock." 
  ::= { f3PtpStatusChangeNotifications 2 }

f3PtpBCStatusChangeTrap NOTIFICATION-TYPE
    OBJECTS {
        f3PtpBCClockClass
    }
    STATUS  current
    DESCRIPTION
            "This trap is sent there is a status change on the Boundary Clock." 
  ::= { f3PtpStatusChangeNotifications 3 }

f3PtpDynamicRemoteSlaveStatusChangeTrap NOTIFICATION-TYPE
    OBJECTS {
        f3PtpDynamicRemoteSlaveClockIdentity,
        f3PtpDynamicRemoteSlaveIpV4Address,
        f3PtpDynamicRemoteSlaveSyncMsgRate,
        f3PtpDynamicRemoteSlaveDelayRspMsgRate,
        f3PtpDynamicRemoteSlaveAnnounceMsgRate
    }
    STATUS  current
    DESCRIPTION
            "This trap is sent there is a status change on the Dynamic Remote Slave." 
  ::= { f3PtpStatusChangeNotifications 4 }


f3PtpL3DynamicRemoteSlaveStatusChangeTrap NOTIFICATION-TYPE
    OBJECTS {
        f3PtpL3DynamicRemoteSlaveClockIdentity,
        f3PtpL3DynamicRemoteSlaveIpV4Address,
        f3PtpL3DynamicRemoteSlaveSyncMsgRate,
        f3PtpL3DynamicRemoteSlaveDelayRspMsgRate,
        f3PtpL3DynamicRemoteSlaveAnnounceMsgRate
    }
    STATUS  current
    DESCRIPTION
            "This trap is sent there is a status change on the Dynamic Remote Slave." 
  ::= { f3PtpStatusChangeNotifications 5 }

--
-- CONFORMANCE
--
f3PtpCompliances OBJECT IDENTIFIER ::= {f3PtpConformance 1}
f3PtpGroups      OBJECT IDENTIFIER ::= {f3PtpConformance 2}

f3PtpCompliance MODULE-COMPLIANCE
    STATUS  current
    DESCRIPTION
            "Describes the requirements for conformance to the F3 PTP
             group."
    MODULE  -- this module
        MANDATORY-GROUPS {
              f3PtpObjectGroup, f3PtpPerfObjectGroup, f3PtpPerfNotifGroup,
              f3PtpStatusChangeNotifGroup
        }
    ::= { f3PtpCompliances 1 }

f3PtpObjectGroup OBJECT-GROUP
    OBJECTS {
      f3PtpTCIndex, f3PtpTCAlias, f3PtpTCAdminState,
      f3PtpTCOperationalState, f3PtpTCSecondaryState,
      f3PtpTCServiceFlow, f3PtpTCDelayMechanism, 
      f3PtpTCSync, f3PtpTCClockIdentity, f3PtpTCStorageType, f3PtpTCRowStatus,
      f3PtpTCPtpProfile,

      f3PtpTCVirtualPortIndex, f3PtpTCVirtualPortAlias,
      f3PtpTCVirtualPortAdminState,
      f3PtpTCVirtualPortOperationalState, f3PtpTCVirtualPortSecondaryState,
      f3PtpTCVirtualPortIdentity, f3PtpTCVirtualPortFlowPoint,
      f3PtpTCVirtualPortStorageType, f3PtpTCVirtualPortRowStatus,

      f3PtpTSIndex, f3PtpTSAlias, f3PtpTSAdminState,
      f3PtpTSOperationalState, f3PtpTSSecondaryState,
      f3PtpTSClockIdentity, f3PtpTSDomainNumber, f3PtpTSSync,
      f3PtpTSCurrentTOD, f3PtpTSSelectedPacketClock, 
      f3PtpTSClockRecoveryMode, f3PtpTSClockRecoveryState,
      f3PtpTSClockSyncEEnabled, f3PtpTSClockQLModeEnabled,
      f3PtpTSClockExpectedQL, f3PtpTSClockAssumedQL,
      f3PtpTSClockReceivedQL, f3PtpTSStorageType, f3PtpTSRowStatus,

      f3PtpTSTimeTraceabilityStatus, f3PtpTSTimeSinceTimeTraceabilityChanged,
      f3PtpTSFreqTraceabilityStatus, f3PtpTSTimeSinceFreqTraceabilityChanged,
      f3PtpTSFreqRecoveryTarget, f3PtpTSCurrentCRScore,
      f3PtpTSTimeLastCRScore, f3PtpTSTargetPhaseRecoveryAccuracy,
      f3PtpTSCurrentPRScore, f3PtpTSTimeLastPRScore,
      f3PtpTSClockClass,
      f3PtpTSClockAccuracy,
      f3PtpTSTimeSource,
      f3PtpTSPhaseRecoveryState, 
      f3PtpTSTimeHoldoverAccuracy,

      f3PtpSOOCIndex, f3PtpSOOCName, f3PtpSOOCAlias,
      f3PtpSOOCAdminState, f3PtpSOOCOperationalState, 
      f3PtpSOOCSecondaryState, f3PtpSOOCServiceFlow,
      f3PtpSOOCMasterClockType, f3PtpSOOCUnicastMessageNegEnabled,
      f3PtpSOOCMasterDelayMechanism, f3PtpSOOCMasterPriority,
      f3PtpSOOCMasterIpProtocol, f3PtpSOOCSlaveIpV4Address,
      f3PtpSOOCSlaveIpV4SubnetMask, f3PtpSOOCMasterIpV4Address,
      f3PtpSOOCIpPriorityMapMode, f3PtpSOOCIpPriority,
      f3PtpSOOCMasterLeaseDuration, f3PtpSOOCMasterAnnounceMsgRate,
      f3PtpSOOCMasterAnnounceMsgReceiptTimeout, 
      f3PtpSOOCMasterSyncMsgRate, f3PtpSOOCMasterSyncReceiptTimeout,
      f3PtpSOOCMasterDelayRspMsgRate, f3PtpSOOCMasterDelayRspReceiptTimeout,
      f3PtpSOOCMasterRequestUnicastTimeout, f3PtpSOOCMasterRequestUnicastRestartTimer,
      f3PtpSOOCCurrentOffsetFromMaster, f3PtpSOOCAnnounceMsgClockClass,
      f3PtpSOOCLastReceivedAnnounceMsg, f3PtpSOOCLastReceivedSyncMsg,
      f3PtpSOOCLastReceivedDelayRspMsg, f3PtpSOOCRecentMeanPathDelay,
      f3PtpSOOCRecentSyncPDV,
      f3PtpSOOCStorageType, f3PtpSOOCRowStatus,
      f3PtpSOOCRecentSyncPathDelay, f3PtpSOOCSoocProtectionState,
      f3PtpSOOCSoocWtr, f3PtpSOOCSoocClockClass,
      f3PtpSOOCSoocClockRecoveryState,f3PtpSOOCSoocPhaseRecoveryState,
      f3PtpSOOCE2eDelayAsymmetryComp, f3PtpSOOCE2eAutoAsymmetryCompStatus,
      f3PtpSOOCE2eDelayAsymmetry, f3PtpSOOCSoocLockOutControl,
      f3PtpSOOCSlaveIpV6Address,f3PtpSOOCSlaveIpV6AddrPrefixLength,f3PtpSOOCMasterIpV6Address,
      f3PtpSOOCMinimumExpectedClockClass, f3PtpSOOCMasterMessageMode,
      f3PtpSOOCDefaultGatewayControl,f3PtpSOOCGateway,f3PtpSOOCIpV6Gateway, f3PtpSOOCAlgorithmPtpAware,
             
      f3PtpOCSlaveVirtualPortIndex, f3PtpOCSlaveVirtualPortAlias,
      f3PtpOCSlaveVirtualPortAdminState,
      f3PtpOCSlaveVirtualPortOperationalState, 
      f3PtpOCSlaveVirtualPortSecondaryState,
      f3PtpOCSlaveVirtualPortIdentity, f3PtpOCSlaveVirtualPortFlowPoint,
      f3PtpOCSlaveVirtualPortState, f3PtpOCSlaveVirtualPortStorageType,
      f3PtpOCSlaveVirtualPortRowStatus,

      f3PtpAccPortFlowPointIndex, f3PtpAccPortFlowPointAlias,
      f3PtpAccPortFlowPointAdminState, f3PtpAccPortFlowPointOperationalState, 
      f3PtpAccPortFlowPointSecondaryState, f3PtpAccPortFlowPointType,
      f3PtpAccPortFlowPointClock, f3PtpAccPortFlowPointService,               
      f3PtpAccPortFlowPointOuterVlanEtherType,
      f3PtpAccPortFlowPointOuterVlanMemberList,
      f3PtpAccPortFlowPointOuterUntaggedEnabled,
      f3PtpAccPortFlowPointInner1VlanEtherType,
      f3PtpAccPortFlowPointInner1VlanMemberList,
      f3PtpAccPortFlowPointInner1UntaggedEnabled,
      f3PtpAccPortFlowPointInner2VlanEtherType,
      f3PtpAccPortFlowPointInner2VlanMemberList,
      f3PtpAccPortFlowPointInner2UntaggedEnabled,
      f3PtpAccPortFlowPointStorageType,
      f3PtpAccPortFlowPointRowStatus,
      f3PtpAccPortFlowPointCOS,
      f3PtpAccPortFlowPointCIRLo,
      f3PtpAccPortFlowPointCIRHi,
      f3PtpAccPortFlowPointEIRLo,
      f3PtpAccPortFlowPointEIRHi,
      f3PtpAccPortFlowPointBufferSize,
      f3PtpAccPortFlowPointLoopAvoidance,
      f3PtpAccPortFlowPointRefConnectGuardFlow,
      f3PtpAccPortFlowPointSecureState,
      f3PtpAccPortFlowPointSecureBlockingEnabled,

      f3PtpNetPortFlowPointIndex, f3PtpNetPortFlowPointAlias,
      f3PtpNetPortFlowPointAdminState, f3PtpNetPortFlowPointOperationalState, 
      f3PtpNetPortFlowPointSecondaryState, f3PtpNetPortFlowPointType,
      f3PtpNetPortFlowPointClock, f3PtpNetPortFlowPointService,               
      f3PtpNetPortFlowPointOuterVlanEtherType,
      f3PtpNetPortFlowPointOuterVlanMemberList,
      f3PtpNetPortFlowPointOuterUntaggedEnabled,
      f3PtpNetPortFlowPointInner1VlanEtherType,
      f3PtpNetPortFlowPointInner1VlanMemberList,
      f3PtpNetPortFlowPointInner1UntaggedEnabled,
      f3PtpNetPortFlowPointInner2VlanEtherType,
      f3PtpNetPortFlowPointInner2VlanMemberList,
      f3PtpNetPortFlowPointInner2UntaggedEnabled,
      f3PtpNetPortFlowPointStorageType,
      f3PtpNetPortFlowPointRowStatus,
      f3PtpNetPortFlowPointCOS,
      f3PtpNetPortFlowPointCIRLo,
      f3PtpNetPortFlowPointCIRHi,
      f3PtpNetPortFlowPointEIRLo,
      f3PtpNetPortFlowPointEIRHi,
      f3PtpNetPortFlowPointBufferSize,
      f3PtpNetPortFlowPointLoopAvoidance,
      f3PtpNetPortFlowPointRefConnectGuardFlow,
      f3PtpNetPortFlowPointSecureState,
      f3PtpNetPortFlowPointSecureBlockingEnabled,

      f3PtpEthernetAccPortDelayAsymmetry, f3PtpEthernetNetPortDelayAsymmetry,
      f3PtpSysTimeOfDayClock,      
       
      f3PtpTrafficPortFlowPointIndex,
      f3PtpTrafficPortFlowPointAlias,      
      f3PtpTrafficPortFlowPointAdminState,
      f3PtpTrafficPortFlowPointOperationalState,
      f3PtpTrafficPortFlowPointSecondaryState,      
      f3PtpTrafficPortFlowPointType,
      f3PtpTrafficPortFlowPointClock,
      f3PtpTrafficPortFlowPointService,
      f3PtpTrafficPortFlowPointOuterVlanEtherType,
      f3PtpTrafficPortFlowPointOuterVlanMemberList,
      f3PtpTrafficPortFlowPointOuterUntaggedEnabled,
      f3PtpTrafficPortFlowPointInner1VlanEtherType,
      f3PtpTrafficPortFlowPointInner1VlanMemberList,
      f3PtpTrafficPortFlowPointInner1UntaggedEnabled,
      f3PtpTrafficPortFlowPointInner2VlanEtherType,
      f3PtpTrafficPortFlowPointInner2VlanMemberList,
      f3PtpTrafficPortFlowPointInner2UntaggedEnabled,      
      f3PtpTrafficPortFlowPointStorageType,
      f3PtpTrafficPortFlowPointRowStatus,
      f3PtpTrafficPortFlowPointCOS,
      f3PtpTrafficPortFlowPointCIRLo,
      f3PtpTrafficPortFlowPointCIRHi,
      f3PtpTrafficPortFlowPointEIRLo,
      f3PtpTrafficPortFlowPointEIRHi,
      f3PtpTrafficPortFlowPointAssociatedQueueProfile,
      f3PtpTrafficPortFlowPointLoopAvoidance,
      
      f3PtpTrafficPortFlowPointBufferSize,
      f3PtpEthernetTrafficPortDelayAsymmetry,

      f3PtpPTPClockIndex,
      f3PtpPTPClockAdminState,
      f3PtpPTPClockAlias,                      
      f3PtpPTPClockOperationalState,                
      f3PtpPTPClockSecondaryState,                 
      f3PtpPTPClockProfile,                         
      f3PtpPTPClockClockType,                       
      f3PtpPTPClockOperationalMode,                 
      f3PtpPTPClockClockIdentity,                   
      f3PtpPTPClockDomainNumber,                    
      f3PtpPTPClockTimeSource,                      
      f3PtpPTPClockPriority1,                       
      f3PtpPTPClockPriority2,                       
      f3PtpPTPClockLocalPriority,                   
      f3PtpPTPClockClockAccuracy,                   
      f3PtpPTPClockScaledLogVariance,               
      f3PtpPTPClockSyncEid,                         
      f3PtpPTPClockCurrentTimeOfDay,                
      f3PtpPTPClockActiveSlavePort,                 
      f3PtpPTPClockClockRecoveryState,              
      f3PtpPTPClockPhaseRecoveryState,              
      f3PtpPTPClockTimeTraceabilityStatus,          
      f3PtpPTPClockTimeSinceTimeTraceabilityChanged,
      f3PtpPTPClockFreqTraceabilityStatus,          
      f3PtpPTPClockTimeSinceFreqTraceabilityChanged,
      f3PtpPTPClockClockSyncEEnabled, 
      f3PtpPTPClockClockQLModeEnabled, 
      f3PtpPTPClockClockExpectedQL,
      f3PtpPTPClockClockAssumedQL,   
      f3PtpPTPClockClockReceivedQL,    
      f3PtpPTPClockCurrentOffsetFromMaster,
      f3PtpPTPClockRecentMeanPathDelay,
      f3PtpPTPClockRecentSyncPDV,
      f3PtpPTPClockClockClass,
      f3PtpPTPClockPhysicalEntityIndex,
      f3PtpPTPClockActiveGrantsAnnounceService,
      f3PtpPTPClockActiveGrantsSyncService,
      f3PtpPTPClockActiveGrantsDelayRequestService,
      f3PtpPTPClockMaxStepRemoved,
      f3PtpPTPClockServiceAvailableTime,
      f3PtpPTPClockServiceUnavailableTime,
      f3PtpPTPClockServiceAvailablePercentage,
      f3PtpPTPClockGrandMasterID,
      f3PtpPTPClockTimeInaccuracy,
      f3PtpPTPClockNetworkTimeInaccuracy,
      f3PtpPTPClockApplicationMode,
      f3PtpPTPClockRecoveryMode,

      f3PtpPTPClockStorageType,
      f3PtpPTPClockRowStatus,
      f3PtpPTPClockCurrentOffsetFromMasterScaled,
      f3PtpPTPClockRecentMeanPathDelayScaled,
      f3PtpPTPClockRecentSyncPDVScaled,
      f3PtpSynchronizationNotAssured,
      
      
       f3PtpPTPPortIndex,                 
       f3PtpPTPPortAdminState, 
       f3PtpPTPPortAlias,           
       f3PtpPTPPortOperationalState,      
       f3PtpPTPPortSecondaryState,        
       f3PtpPTPPortPeerPortIdentity,      
       f3PtpPTPPortLocalPriority,         
       f3PtpPTPPortPtpFlowPointEid,       
       f3PtpPTPPortNotSlave,              
       f3PtpPTPPortTxDestMacAddress,      
       f3PtpPTPPortSyncMessageRate,       
       f3PtpPTPPortmDelayReqRespMsgRate,  
       f3PtpPTPPortmAnnounceMsgRate,      
       f3PtpPTPPortAnnounceReceiptTimeout,
       f3PtpPTPPortSyncReceiptTimeout,    
       f3PtpPTPPortDelayRespTimeout,      
       f3PtpPTPPortPortState,             
       f3PtpPTPPortBmcaDecisionCode,      
       f3PtpPTPPortClockClass,        
       f3PtpPTPPortPeerPortMacAddress,
       f3PtpPTPPortRowStatus,
       f3PtpPTPPortPortIdentity,
       f3PtpPTPPortMasterClockType,
       f3PtpPTPPortLastRcvdAnnounceMsg,
       f3PtpPTPPortLastRcvdSyncMsg,
       f3PtpPTPPortLastRcvdDelayReqMsg,
       f3PtpPTPPortLastRcvdDelayRspMsg,
       f3PtpPTPPortMasterOnly,
       f3PtpPTPPortPeerClockClass,
       f3PtpPTPPortMinimumExpectedClockClass,
       f3PtpPTPPortDelayAsymmetryComp,
       f3PtpPTPPortAutoAsymmetryCompStatus,
       f3PtpPTPPortDelayAsymmetry,
       f3PtpPTPPortVirtualPortCtrl,
       f3PtpPTPPortDelayResponderType,
       f3PtpPTPPortTimeTraceable,
       f3PtpPTPPortFrequencyTraceable,
       f3PtpPTPPortDelayMechanism,
       f3PtpPTPPortForcePRTCClockQuality,
       f3PtpPTPPortScaledLogVariance,
       f3PtpPTPPortClockAccuracy,
       f3PtpPTPPortGMIdentity,
       f3PtpPTPPortStepsRemoved,
       f3PtpPTPPortIfName,

       f3PtpL2DynamicRemoteSlaveIndex,
       f3PtpL2DynamicRemoteSlavePortIdentity,
       f3PtpL2DynamicRemoteSlaveClockIdentity,
       f3PtpL2DynamicRemoteSlaveMacAddress,
       f3PtpL2DynamicRemoteSlaveRowStatus,
       f3PtpL2DynamicRemoteSlaveStorageType,


       f3PtpL3PTPPortIndex,
       f3PtpL3PTPPortAdminState,
       f3PtpL3PTPPortAlias,          
       f3PtpL3PTPPortOperationalState,  
       f3PtpL3PTPPortSecondaryState,
       f3PtpL3PTPPortPortIdentity,    
       f3PtpL3PTPPortLocalPriority,         
       f3PtpL3PTPPortPtpFlowPointEid,         
       f3PtpL3PTPPortSyncMessageRate,   
       f3PtpL3PTPPortDelayReqRespMsgRate,
       f3PtpL3PTPPortAnnounceMsgRate,
       f3PtpL3PTPPortAnnounceReceiptTimeout,                            
       f3PtpL3PTPPortSyncReceiptTimeout,                            
       f3PtpL3PTPPortDelayRespTimeout,  
       f3PtpL3PTPPortPortState,
       f3PtpL3PTPPortBmcaDecisionCode, 
       f3PtpL3PTPPortPeerClockClass, 
       f3PtpL3PTPPortMinimumExpectedClockClass,
       f3PtpL3PTPPortIpProtocol,
       f3PtpL3PTPPortIfName,
       f3PtpL3PTPPortIpPriorityMapMode,
       f3PtpL3PTPPortIpPriority,
       f3PtpL3PTPPortIpV4Address,
       f3PtpL3PTPPortIpV4SubnetMask,
       f3PtpL3PTPPortIpV6Address,             
       f3PtpL3PTPPortIpV6AddrPrefixLength,
       f3PtpL3PTPPortDefaultGatewayControl,
       f3PtpL3PTPPortGateway,
       f3PtpL3PTPPortIpV6Gateway,
       f3PtpL3PTPPortUnicastMessageNegEnabled,
       f3PtpL3PTPPortTransmitDuration,
       f3PtpL3PTPPortRequestUnicastTimeout,
       f3PtpL3PTPPortRequestUnicastRestartTimer,
       f3PtpL3PTPPortMasterIpV4Address,
       f3PtpL3PTPPortMasterIpV6Address,
       f3PtpL3PTPPortDelayAsymmetryComp,
       f3PtpL3PTPPortAutoAsymmetryCompStatus,
       f3PtpL3PTPPortDelayAsymmetry,
       f3PtpL3PTPPortStorageType,
       f3PtpL3PTPPortRowStatus,
       f3PtpL3PTPPortDelayReqDestIpAddrType,
       f3PtpL3PTPPortScaledLogVariance,
       f3PtpL3PTPPortClockAccuracy,
       f3PtpL3PTPPortGMIdentity,
       f3PtpL3PTPPortStepsRemoved,
       f3PtpL3PTPPortVirtualPortCtrl,
       f3PtpL3PTPPortLastRcvdAnnounceMsg,
       f3PtpL3PTPPortLastRcvdSyncMsg,
       f3PtpL3PTPPortLastRcvdDelayReqMsg,
       f3PtpL3PTPPortLastRcvdDelayRspMsg,
       
       f3PtpL3PTPPortMasterOnly,
       f3PtpL3PTPPortMaxDelayRespMessageRate,
       f3PtpL3PTPPortMaxSyncMessageRate,
       f3PtpL3PTPPortMaxAnnounceMessageRate,
       f3PtpL3PTPPortMaxSlavesSupported,
       f3PtpL3PTPPortMaxLeaseDuration
    
    }

    STATUS  current
    DESCRIPTION
        "A collection of objects used to manage the F3 PTP Configuration data."
    ::= { f3PtpGroups 1 }

f3PtpPerfObjectGroup OBJECT-GROUP
    OBJECTS {
    f3PtpAccPortFlowPointStatsIndex, f3PtpAccPortFlowPointStatsIntervalType,
    f3PtpAccPortFlowPointStatsValid, f3PtpAccPortFlowPointStatsAction,
    f3PtpAccPortFlowPointStatsAnnouncesRx, f3PtpAccPortFlowPointStatsAnnouncesTx,
    f3PtpAccPortFlowPointStatsSyncsRx, f3PtpAccPortFlowPointStatsSyncsTx,
    f3PtpAccPortFlowPointStatsFollowupsRx, f3PtpAccPortFlowPointStatsFollowupsTx,
    f3PtpAccPortFlowPointStatsDelayReqsRx, f3PtpAccPortFlowPointStatsDelayReqsTx,
    f3PtpAccPortFlowPointStatsDelayRspsRx, f3PtpAccPortFlowPointStatsDelayRspsTx,
    f3PtpAccPortFlowPointStatsPDelayReqsRx, f3PtpAccPortFlowPointStatsPDelayReqsTx,
    f3PtpAccPortFlowPointStatsPDelayRspsRx, f3PtpAccPortFlowPointStatsPDelayRspsTx,
    f3PtpAccPortFlowPointStatsPDelayRspFollowupsRx, f3PtpAccPortFlowPointStatsPDelayRspFollowupsTx,
    f3PtpAccPortFlowPointStatsSignalingRx, f3PtpAccPortFlowPointStatsSignalingTx,
    f3PtpAccPortFlowPointStatsMgmtFramesRx, f3PtpAccPortFlowPointStatsMgmtFramesTx,
    f3PtpAccPortFlowPointStatsPtpUnknownsRx, f3PtpAccPortFlowPointStatsPtpUnknownsTx,
    f3PtpAccPortFlowPointStatsAvgSyncResTime,
    f3PtpAccPortFlowPointStatsMinSyncResTime, f3PtpAccPortFlowPointStatsMaxSyncResTime,
    f3PtpAccPortFlowPointStatsAvgDelayReqResTime, f3PtpAccPortFlowPointStatsMinDelayReqResTime,
    f3PtpAccPortFlowPointStatsMaxDelayReqResTime,
    f3PtpAccPortFlowPointStatsMinPDelayReqResTime,
    f3PtpAccPortFlowPointStatsMaxPDelayReqResTime,
    f3PtpAccPortFlowPointStatsAvgPDelayReqResTime,
    f3PtpAccPortFlowPointStatsMinPDelayRspResTime,
    f3PtpAccPortFlowPointStatsMaxPDelayRspResTime,
    f3PtpAccPortFlowPointStatsAvgPDelayRspResTime,
    f3PtpAccPortFlowPointStatsDestMciNoMatchDiscards,

    f3PtpAccPortFlowPointHistoryIndex, f3PtpAccPortFlowPointHistoryTime,
    f3PtpAccPortFlowPointHistoryValid, f3PtpAccPortFlowPointHistoryAction,
    f3PtpAccPortFlowPointHistoryAnnouncesRx, f3PtpAccPortFlowPointHistoryAnnouncesTx,
    f3PtpAccPortFlowPointHistorySyncsRx, f3PtpAccPortFlowPointHistorySyncsTx,
    f3PtpAccPortFlowPointHistoryFollowupsRx, f3PtpAccPortFlowPointHistoryFollowupsTx,
    f3PtpAccPortFlowPointHistoryDelayReqsRx, f3PtpAccPortFlowPointHistoryDelayReqsTx,
    f3PtpAccPortFlowPointHistoryDelayRspsRx, f3PtpAccPortFlowPointHistoryDelayRspsTx,
    f3PtpAccPortFlowPointHistoryPDelayReqsRx, f3PtpAccPortFlowPointHistoryPDelayReqsTx,
    f3PtpAccPortFlowPointHistoryPDelayRspsRx, f3PtpAccPortFlowPointHistoryPDelayRspsTx,
    f3PtpAccPortFlowPointHistoryPDelayRspFollowupsRx, f3PtpAccPortFlowPointHistoryPDelayRspFollowupsTx,
    f3PtpAccPortFlowPointHistorySignalingRx, f3PtpAccPortFlowPointHistorySignalingTx,
    f3PtpAccPortFlowPointHistoryMgmtFramesRx, f3PtpAccPortFlowPointHistoryMgmtFramesTx,
    f3PtpAccPortFlowPointHistoryPtpUnknownsRx, f3PtpAccPortFlowPointHistoryPtpUnknownsTx,
    f3PtpAccPortFlowPointHistoryAvgSyncResTime,
    f3PtpAccPortFlowPointHistoryMinSyncResTime, f3PtpAccPortFlowPointHistoryMaxSyncResTime,
    f3PtpAccPortFlowPointHistoryAvgDelayReqResTime, f3PtpAccPortFlowPointHistoryMinDelayReqResTime,
    f3PtpAccPortFlowPointHistoryMaxDelayReqResTime,
    f3PtpAccPortFlowPointHistoryMinPDelayReqResTime,
    f3PtpAccPortFlowPointHistoryMaxPDelayReqResTime,
    f3PtpAccPortFlowPointHistoryAvgPDelayReqResTime,
    f3PtpAccPortFlowPointHistoryMinPDelayRspResTime,
    f3PtpAccPortFlowPointHistoryMaxPDelayRspResTime,
    f3PtpAccPortFlowPointHistoryAvgPDelayRspResTime,
    f3PtpAccPortFlowPointHistoryDestMciNoMatchDiscards,

    f3PtpAccPortFlowPointThresholdIndex, f3PtpAccPortFlowPointThresholdInterval,
    f3PtpAccPortFlowPointThresholdVariable, f3PtpAccPortFlowPointThresholdValueLo,
    f3PtpAccPortFlowPointThresholdValueHi, f3PtpAccPortFlowPointThresholdMonValue,

    f3PtpNetPortFlowPointStatsIndex, f3PtpNetPortFlowPointStatsIntervalType,
    f3PtpNetPortFlowPointStatsValid, f3PtpNetPortFlowPointStatsAction,
    f3PtpNetPortFlowPointStatsAnnouncesRx, f3PtpNetPortFlowPointStatsAnnouncesTx,
    f3PtpNetPortFlowPointStatsSyncsRx, f3PtpNetPortFlowPointStatsSyncsTx,
    f3PtpNetPortFlowPointStatsFollowupsRx, f3PtpNetPortFlowPointStatsFollowupsTx,
    f3PtpNetPortFlowPointStatsDelayReqsRx, f3PtpNetPortFlowPointStatsDelayReqsTx,
    f3PtpNetPortFlowPointStatsDelayRspsRx, f3PtpNetPortFlowPointStatsDelayRspsTx,
    f3PtpNetPortFlowPointStatsPDelayReqsRx, f3PtpNetPortFlowPointStatsPDelayReqsTx,
    f3PtpNetPortFlowPointStatsPDelayRspsRx, f3PtpNetPortFlowPointStatsPDelayRspsTx,
    f3PtpNetPortFlowPointStatsPDelayRspFollowupsRx, f3PtpNetPortFlowPointStatsPDelayRspFollowupsTx,
    f3PtpNetPortFlowPointStatsSignalingRx, f3PtpNetPortFlowPointStatsSignalingTx,
    f3PtpNetPortFlowPointStatsMgmtFramesRx, f3PtpNetPortFlowPointStatsMgmtFramesTx,
    f3PtpNetPortFlowPointStatsPtpUnknownsRx, f3PtpNetPortFlowPointStatsPtpUnknownsTx,
    f3PtpNetPortFlowPointStatsAvgSyncResTime,
    f3PtpNetPortFlowPointStatsMinSyncResTime, f3PtpNetPortFlowPointStatsMaxSyncResTime,
    f3PtpNetPortFlowPointStatsAvgDelayReqResTime, f3PtpNetPortFlowPointStatsMinDelayReqResTime,
    f3PtpNetPortFlowPointStatsMaxDelayReqResTime,
    f3PtpNetPortFlowPointStatsMinPDelayReqResTime,
    f3PtpNetPortFlowPointStatsMaxPDelayReqResTime,
    f3PtpNetPortFlowPointStatsAvgPDelayReqResTime,
    f3PtpNetPortFlowPointStatsMinPDelayRspResTime,
    f3PtpNetPortFlowPointStatsMaxPDelayRspResTime,
    f3PtpNetPortFlowPointStatsAvgPDelayRspResTime,
    f3PtpNetPortFlowPointStatsDestMciNoMatchDiscards,

    f3PtpNetPortFlowPointHistoryIndex, f3PtpNetPortFlowPointHistoryTime,
    f3PtpNetPortFlowPointHistoryValid, f3PtpNetPortFlowPointHistoryAction,
    f3PtpNetPortFlowPointHistoryAnnouncesRx, f3PtpNetPortFlowPointHistoryAnnouncesTx,
    f3PtpNetPortFlowPointHistorySyncsRx, f3PtpNetPortFlowPointHistorySyncsTx,
    f3PtpNetPortFlowPointHistoryFollowupsRx, f3PtpNetPortFlowPointHistoryFollowupsTx,
    f3PtpNetPortFlowPointHistoryDelayReqsRx, f3PtpNetPortFlowPointHistoryDelayReqsTx,
    f3PtpNetPortFlowPointHistoryDelayRspsRx, f3PtpNetPortFlowPointHistoryDelayRspsTx,
    f3PtpNetPortFlowPointHistoryPDelayReqsRx, f3PtpNetPortFlowPointHistoryPDelayReqsTx,
    f3PtpNetPortFlowPointHistoryPDelayRspsRx, f3PtpNetPortFlowPointHistoryPDelayRspsTx,
    f3PtpNetPortFlowPointHistoryPDelayRspFollowupsRx, f3PtpNetPortFlowPointHistoryPDelayRspFollowupsTx,
    f3PtpNetPortFlowPointHistorySignalingRx, f3PtpNetPortFlowPointHistorySignalingTx,
    f3PtpNetPortFlowPointHistoryMgmtFramesRx, f3PtpNetPortFlowPointHistoryMgmtFramesTx,
    f3PtpNetPortFlowPointHistoryPtpUnknownsRx, f3PtpNetPortFlowPointHistoryPtpUnknownsTx,
    f3PtpNetPortFlowPointHistoryAvgSyncResTime,
    f3PtpNetPortFlowPointHistoryMinSyncResTime, f3PtpNetPortFlowPointHistoryMaxSyncResTime,
    f3PtpNetPortFlowPointHistoryAvgDelayReqResTime, f3PtpNetPortFlowPointHistoryMinDelayReqResTime,
    f3PtpNetPortFlowPointHistoryMaxDelayReqResTime,
    f3PtpNetPortFlowPointHistoryMinPDelayReqResTime,
    f3PtpNetPortFlowPointHistoryMaxPDelayReqResTime,
    f3PtpNetPortFlowPointHistoryAvgPDelayReqResTime,
    f3PtpNetPortFlowPointHistoryMinPDelayRspResTime,
    f3PtpNetPortFlowPointHistoryMaxPDelayRspResTime,
    f3PtpNetPortFlowPointHistoryAvgPDelayRspResTime,
    f3PtpNetPortFlowPointHistoryDestMciNoMatchDiscards,

    f3PtpNetPortFlowPointThresholdIndex, f3PtpNetPortFlowPointThresholdInterval,
    f3PtpNetPortFlowPointThresholdVariable, f3PtpNetPortFlowPointThresholdValueLo,
    f3PtpNetPortFlowPointThresholdValueHi, f3PtpNetPortFlowPointThresholdMonValue,

    f3PtpSOOCStatsIndex, f3PtpSOOCStatsIntervalType, f3PtpSOOCStatsValid,
    f3PtpSOOCStatsAction, f3PtpSOOCStatsMinOffsetFromMaster, f3PtpSOOCStatsMaxOffsetFromMaster,
    f3PtpSOOCStatsAvgOffsetFromMaster, f3PtpSOOCStatsMinMeanPathDelay,
    f3PtpSOOCStatsMaxMeanPathDelay, f3PtpSOOCStatsAvgMeanPathDelay,
    f3PtpSOOCStatsMinSyncPathDelay, f3PtpSOOCStatsMaxSyncPathDelay,
    f3PtpSOOCStatsAvgSyncPathDelay, f3PtpSOOCStatsMinSyncPDV,
    f3PtpSOOCStatsMaxSyncPDV, f3PtpSOOCStatsAvgSyncPDV, f3PtpSOOCStatsMgmtMsgsDiscarded,
    f3PtpSOOCStatsInvalidMsgLenDiscards, f3PtpSOOCStatsUnknownMasterDiscards,
    f3PtpSOOCStatsUnknownDomainDiscards, f3PtpSOOCStatsMulticastAnnounceDiscards,
    f3PtpSOOCStatsOutOfSeqAnnounceMsgs, f3PtpSOOCStatsMulticastSyncDiscards,
    f3PtpSOOCStatsTwoStepSyncDiscards, f3PtpSOOCStatsFollowupDiscards,
    f3PtpSOOCStatsDelayReqDiscards, f3PtpSOOCStatsPDelayReqDiscards,
    f3PtpSOOCStatsPDelayRspDiscards, f3PtpSOOCStatsPDelayFollowupDiscards,
    f3PtpSOOCStatsInvalidTLVLenDiscards, f3PtpSOOCStatsInvalidTLVTypeDiscards,
    f3PtpSOOCStatsMaxFwdFlowWeight,
    f3PtpSOOCStatsAvgFwdFlowWeight,
    f3PtpSOOCStatsMinRevFlowWeight,
    f3PtpSOOCStatsMaxRevFlowWeight,
    f3PtpSOOCStatsAvgRevFlowWeight,
    f3PtpSOOCStatsNumClockRecTransients,

    f3PtpSOOCHistoryIndex, f3PtpSOOCHistoryTime, f3PtpSOOCHistoryValid,
    f3PtpSOOCHistoryAction, f3PtpSOOCHistoryMinOffsetFromMaster, f3PtpSOOCHistoryMaxOffsetFromMaster,
    f3PtpSOOCHistoryAvgOffsetFromMaster, f3PtpSOOCHistoryMinMeanPathDelay,
    f3PtpSOOCHistoryMaxMeanPathDelay, f3PtpSOOCHistoryAvgMeanPathDelay,
    f3PtpSOOCHistoryMinSyncPathDelay, f3PtpSOOCHistoryMaxSyncPathDelay,
    f3PtpSOOCHistoryAvgSyncPathDelay, f3PtpSOOCHistoryMinSyncPDV,
    f3PtpSOOCHistoryMaxSyncPDV, f3PtpSOOCHistoryAvgSyncPDV, f3PtpSOOCHistoryMgmtMsgsDiscarded,
    f3PtpSOOCHistoryInvalidMsgLenDiscards, f3PtpSOOCHistoryUnknownMasterDiscards,
    f3PtpSOOCHistoryUnknownDomainDiscards, f3PtpSOOCHistoryMulticastAnnounceDiscards,
    f3PtpSOOCHistoryOutOfSeqAnnounceMsgs, f3PtpSOOCHistoryMulticastSyncDiscards,
    f3PtpSOOCHistoryTwoStepSyncDiscards, f3PtpSOOCHistoryFollowupDiscards,
    f3PtpSOOCHistoryDelayReqDiscards, f3PtpSOOCHistoryPDelayReqDiscards,
    f3PtpSOOCHistoryPDelayRspDiscards, f3PtpSOOCHistoryPDelayFollowupDiscards,
    f3PtpSOOCHistoryInvalidTLVLenDiscards, f3PtpSOOCHistoryInvalidTLVTypeDiscards,
    f3PtpSOOCHistoryMaxFwdFlowWeight,
    f3PtpSOOCHistoryAvgFwdFlowWeight,
    f3PtpSOOCHistoryMinRevFlowWeight,
    f3PtpSOOCHistoryMaxRevFlowWeight,
    f3PtpSOOCHistoryAvgRevFlowWeight,
    f3PtpSOOCHistoryNumClockRecTransients,

    f3PtpSOOCThresholdIndex, f3PtpSOOCThresholdInterval, f3PtpSOOCThresholdVariable,
    f3PtpSOOCThresholdValueLo, f3PtpSOOCThresholdValueHi, f3PtpSOOCThresholdMonValue,

    f3PtpTSStatsIndex, f3PtpTSStatsIntervalType,
    f3PtpTSStatsValid, f3PtpTSStatsAction, f3PtpTSStatsTotalTimeCR5,
    f3PtpTSStatsTotalTimeCR4, f3PtpTSStatsTotalTimeCR3,
    f3PtpTSStatsTotalTimePR5, f3PtpTSStatsTotalTimePR4,
    f3PtpTSStatsTotalTimePR3,

    f3PtpTSHistoryIndex, f3PtpTSHistoryTime, f3PtpTSHistoryValid,
    f3PtpTSHistoryAction, f3PtpTSHistoryTotalTimeCR5,
    f3PtpTSHistoryTotalTimeCR4, f3PtpTSHistoryTotalTimeCR3,
    f3PtpTSHistoryTotalTimePR5, f3PtpTSHistoryTotalTimePR4,
    f3PtpTSHistoryTotalTimePR3,

    f3PtpTSThresholdIndex, f3PtpTSThresholdInterval,
    f3PtpTSThresholdVariable, f3PtpTSThresholdValueLo,
    f3PtpTSThresholdValueHi, f3PtpTSThresholdMonValue,
       
    f3PtpTrafficPortFlowPointStatsIndex,
    f3PtpTrafficPortFlowPointStatsIntervalType,
    f3PtpTrafficPortFlowPointStatsValid,
    f3PtpTrafficPortFlowPointStatsAction,
    f3PtpTrafficPortFlowPointStatsAnnouncesRx,
    f3PtpTrafficPortFlowPointStatsAnnouncesTx,
    f3PtpTrafficPortFlowPointStatsSyncsRx,
    f3PtpTrafficPortFlowPointStatsSyncsTx,
    f3PtpTrafficPortFlowPointStatsFollowupsRx,
    f3PtpTrafficPortFlowPointStatsFollowupsTx,
    f3PtpTrafficPortFlowPointStatsDelayReqsRx,
    f3PtpTrafficPortFlowPointStatsDelayReqsTx,
    f3PtpTrafficPortFlowPointStatsDelayRspsRx,
    f3PtpTrafficPortFlowPointStatsDelayRspsTx,
    f3PtpTrafficPortFlowPointStatsPDelayReqsRx,
    f3PtpTrafficPortFlowPointStatsPDelayReqsTx,
    f3PtpTrafficPortFlowPointStatsPDelayRspsRx,
    f3PtpTrafficPortFlowPointStatsPDelayRspsTx,
    f3PtpTrafficPortFlowPointStatsPDelayRspFollowupsRx,
    f3PtpTrafficPortFlowPointStatsPDelayRspFollowupsTx,
    f3PtpTrafficPortFlowPointStatsSignalingRx,
    f3PtpTrafficPortFlowPointStatsSignalingTx,
    f3PtpTrafficPortFlowPointStatsMgmtFramesRx,
    f3PtpTrafficPortFlowPointStatsMgmtFramesTx,
    f3PtpTrafficPortFlowPointStatsPtpUnknownsRx,
    f3PtpTrafficPortFlowPointStatsPtpUnknownsTx,
    f3PtpTrafficPortFlowPointStatsMinSyncResTime,
    f3PtpTrafficPortFlowPointStatsMaxSyncResTime,
    f3PtpTrafficPortFlowPointStatsAvgSyncResTime,
    f3PtpTrafficPortFlowPointStatsMinDelayReqResTime,
    f3PtpTrafficPortFlowPointStatsMaxDelayReqResTime,
    f3PtpTrafficPortFlowPointStatsAvgDelayReqResTime,
    f3PtpTrafficPortFlowPointStatsMinPDelayReqResTime,
    f3PtpTrafficPortFlowPointStatsMaxPDelayReqResTime,
    f3PtpTrafficPortFlowPointStatsAvgPDelayReqResTime,
    f3PtpTrafficPortFlowPointStatsMinPDelayRspResTime,
    f3PtpTrafficPortFlowPointStatsMaxPDelayRspResTime,
    f3PtpTrafficPortFlowPointStatsAvgPDelayRspResTime,
    f3PtpTrafficPortFlowPointStatsDestMciNoMatchDiscards,
    f3PtpTrafficPortFlowPointStatsTagNoMatchDiscards,
    
    f3PtpTrafficPortFlowPointHistoryIndex,
    f3PtpTrafficPortFlowPointHistoryTime,
    f3PtpTrafficPortFlowPointHistoryValid,
    f3PtpTrafficPortFlowPointHistoryAction,
    f3PtpTrafficPortFlowPointHistoryAnnouncesRx,
    f3PtpTrafficPortFlowPointHistoryAnnouncesTx,
    f3PtpTrafficPortFlowPointHistorySyncsRx,
    f3PtpTrafficPortFlowPointHistorySyncsTx,
    f3PtpTrafficPortFlowPointHistoryFollowupsRx,
    f3PtpTrafficPortFlowPointHistoryFollowupsTx,
    f3PtpTrafficPortFlowPointHistoryDelayReqsRx,
    f3PtpTrafficPortFlowPointHistoryDelayReqsTx,
    f3PtpTrafficPortFlowPointHistoryDelayRspsRx,
    f3PtpTrafficPortFlowPointHistoryDelayRspsTx,
    f3PtpTrafficPortFlowPointHistoryPDelayReqsRx,
    f3PtpTrafficPortFlowPointHistoryPDelayReqsTx,
    f3PtpTrafficPortFlowPointHistoryPDelayRspsRx,
    f3PtpTrafficPortFlowPointHistoryPDelayRspsTx,
    f3PtpTrafficPortFlowPointHistoryPDelayRspFollowupsRx,
    f3PtpTrafficPortFlowPointHistoryPDelayRspFollowupsTx,
    f3PtpTrafficPortFlowPointHistorySignalingRx,
    f3PtpTrafficPortFlowPointHistorySignalingTx,
    f3PtpTrafficPortFlowPointHistoryMgmtFramesRx,
    f3PtpTrafficPortFlowPointHistoryMgmtFramesTx,
    f3PtpTrafficPortFlowPointHistoryPtpUnknownsRx,
    f3PtpTrafficPortFlowPointHistoryPtpUnknownsTx,
    f3PtpTrafficPortFlowPointHistoryMinSyncResTime,
    f3PtpTrafficPortFlowPointHistoryMaxSyncResTime,
    f3PtpTrafficPortFlowPointHistoryAvgSyncResTime,
    f3PtpTrafficPortFlowPointHistoryMinDelayReqResTime,
    f3PtpTrafficPortFlowPointHistoryMaxDelayReqResTime,
    f3PtpTrafficPortFlowPointHistoryAvgDelayReqResTime,
    f3PtpTrafficPortFlowPointHistoryMinPDelayReqResTime,
    f3PtpTrafficPortFlowPointHistoryMaxPDelayReqResTime,
    f3PtpTrafficPortFlowPointHistoryAvgPDelayReqResTime,
    f3PtpTrafficPortFlowPointHistoryMinPDelayRspResTime,
    f3PtpTrafficPortFlowPointHistoryMaxPDelayRspResTime,
    f3PtpTrafficPortFlowPointHistoryAvgPDelayRspResTime,
    f3PtpTrafficPortFlowPointHistoryDestMciNoMatchDiscards,
    f3PtpTrafficPortFlowPointHistoryTagNoMatchDiscards,
    
    f3PtpTrafficPortFlowPointThresholdIndex,
    f3PtpTrafficPortFlowPointThresholdInterval,
    f3PtpTrafficPortFlowPointThresholdVariable,
    f3PtpTrafficPortFlowPointThresholdValueLo,
    f3PtpTrafficPortFlowPointThresholdValueHi,
    f3PtpTrafficPortFlowPointThresholdMonValue,

--    f3PtpPTPClockStatsIndex, f3PtpPTPClockStatsIntervalType,
--    f3PtpPTPClockStatsValid, f3PtpPTPClockStatsAction, f3PtpPTPClockStatsTotalTimeCR5,
--    f3PtpPTPClockStatsTotalTimeCR4, f3PtpPTPClockStatsTotalTimeCR3,
--    f3PtpPTPClockStatsTotalTimePR5, f3PtpPTPClockStatsTotalTimePR4,
--    f3PtpPTPClockStatsTotalTimePR3,

--    f3PtpPTPClockHistoryIndex, f3PtpPTPClockHistoryTime, f3PtpPTPClockHistoryValid,
--    f3PtpPTPClockHistoryAction, f3PtpPTPClockHistoryTotalTimeCR5,
--    f3PtpPTPClockHistoryTotalTimeCR4, f3PtpPTPClockHistoryTotalTimeCR3,
--    f3PtpPTPClockHistoryTotalTimePR5, f3PtpPTPClockHistoryTotalTimePR4,
--    f3PtpPTPClockHistoryTotalTimePR3,

--    f3PtpPTPClockThresholdIndex, f3PtpPTPClockThresholdInterval,
--    f3PtpPTPClockThresholdVariable, f3PtpPTPClockThresholdValueLo,
--    f3PtpPTPClockThresholdValueHi, f3PtpPTPClockThresholdMonValue,

    f3PtpPTPPortStatsIndex,                        
    f3PtpPTPPortStatsIntervalType,
    f3PtpPTPPortStatsValid,
    f3PtpPTPPortStatsAction,
    f3PtpPTPPortStatsAvgAnnounceRate,
    f3PtpPTPPortStatsAvgSyncRate,
    f3PtpPTPPortStatsAvgDelayReqRate,
    f3PtpPTPPortStatsAvgDelayRespRate,
    f3PtpPTPPortStatsMismatchDomainDiscards,
    f3PtpPTPPortStatsMessageWrongTypeDiscards,
    f3PtpPTPPortStatsMessagesWrongLengthDiscards,
    f3PtpPTPPortStatsUnknownMasterDiscards,
    f3PtpPTPPortStatsMinOffsetFromMaster, 
    f3PtpPTPPortStatsMaxOffsetFromMaster,
    f3PtpPTPPortStatsAvgOffsetFromMaster,
    f3PtpPTPPortStatsMinSyncPathDelay,
    f3PtpPTPPortStatsMaxSyncPathDelay,
    f3PtpPTPPortStatsAvgSyncPathDelay,
    f3PtpPTPPortStatsMinMeanPathDelay,
    f3PtpPTPPortStatsMaxMeanPathDelay,
    f3PtpPTPPortStatsAvgMeanPathDelay,
    f3PtpPTPPortStatsMsgMiscDiscards,
    f3PtpPTPPortStatsAvgLinkDelay,f3PtpPTPPortStatsMinLinkDelay,f3PtpPTPPortStatsMaxLinkDelay,


    f3PtpPTPPortHistoryIndex,
    f3PtpPTPPortHistoryTime,
    f3PtpPTPPortHistoryValid,
    f3PtpPTPPortHistoryAction,
    f3PtpPTPPortHistoryAvgAnnounceRate,
    f3PtpPTPPortHistoryAvgSyncRate,
    f3PtpPTPPortHistoryAvgDelayReqRate,
    f3PtpPTPPortHistoryAvgDelayRespRate,
    f3PtpPTPPortHistoryMismatchDomainDiscards,
    f3PtpPTPPortHistoryMessageWrongTypeDiscards,
    f3PtpPTPPortHistoryMessagesWrongLengthDiscards,
    f3PtpPTPPortHistoryUnknownMasterDiscards,
    f3PtpPTPPortHistoryMinOffsetFromMaster,
    f3PtpPTPPortHistoryMaxOffsetFromMaster,
    f3PtpPTPPortHistoryAvgOffsetFromMaster,        
    f3PtpPTPPortHistoryMinSyncPathDelay,
    f3PtpPTPPortHistoryMaxSyncPathDelay,
    f3PtpPTPPortHistoryAvgSyncPathDelay,
    f3PtpPTPPortHistoryMinMeanPathDelay,
    f3PtpPTPPortHistoryMaxMeanPathDelay,
    f3PtpPTPPortHistoryAvgMeanPathDelay,
    f3PtpPTPPortHistoryMsgMiscDiscards,
    f3PtpPTPPortHistoryAvgLinkDelay,f3PtpPTPPortHistoryMinLinkDelay,f3PtpPTPPortHistoryMaxLinkDelay,

    f3PtpPTPPortThresholdIndex, f3PtpPTPPortThresholdInterval,
    f3PtpPTPPortThresholdVariable, f3PtpPTPPortThresholdValueLo,
    f3PtpPTPPortThresholdValueHi, f3PtpPTPPortThresholdMonValue,

    f3PtpL3PTPPortStatsIndex,                        
    f3PtpL3PTPPortStatsIntervalType,
    f3PtpL3PTPPortStatsValid,
    f3PtpL3PTPPortStatsAction,
    f3PtpL3PTPPortStatsAvgAnnounceRate,
    f3PtpL3PTPPortStatsAvgSyncRate,
    f3PtpL3PTPPortStatsAvgDelayReqRate,
    f3PtpL3PTPPortStatsAvgDelayRespRate,
    f3PtpL3PTPPortStatsMismatchDomainDiscards,
    f3PtpL3PTPPortStatsMessageWrongTypeDiscards,
    f3PtpL3PTPPortStatsMessagesWrongLengthDiscards,
    f3PtpL3PTPPortStatsUnknownMasterDiscards,
    f3PtpL3PTPPortStatsMinOffsetFromMaster, 
    f3PtpL3PTPPortStatsMaxOffsetFromMaster,
    f3PtpL3PTPPortStatsAvgOffsetFromMaster,
    f3PtpL3PTPPortStatsMinSyncPathDelay,
    f3PtpL3PTPPortStatsMaxSyncPathDelay,
    f3PtpL3PTPPortStatsAvgSyncPathDelay,
    f3PtpL3PTPPortStatsMinMeanPathDelay,
    f3PtpL3PTPPortStatsMaxMeanPathDelay,
    f3PtpL3PTPPortStatsAvgMeanPathDelay,
    f3PtpL3PTPPortStatsMsgMiscDiscards,

    f3PtpL3PTPPortHistoryIndex,
    f3PtpL3PTPPortHistoryTime,
    f3PtpL3PTPPortHistoryValid,
    f3PtpL3PTPPortHistoryAction,
    f3PtpL3PTPPortHistoryAvgAnnounceRate,
    f3PtpL3PTPPortHistoryAvgSyncRate,
    f3PtpL3PTPPortHistoryAvgDelayReqRate,
    f3PtpL3PTPPortHistoryAvgDelayRespRate,
    f3PtpL3PTPPortHistoryMismatchDomainDiscards,
    f3PtpL3PTPPortHistoryMessageWrongTypeDiscards,
    f3PtpL3PTPPortHistoryMessagesWrongLengthDiscards,
    f3PtpL3PTPPortHistoryUnknownMasterDiscards,
    f3PtpL3PTPPortHistoryMinOffsetFromMaster,
    f3PtpL3PTPPortHistoryMaxOffsetFromMaster,
    f3PtpL3PTPPortHistoryAvgOffsetFromMaster,        
    f3PtpL3PTPPortHistoryMinSyncPathDelay,
    f3PtpL3PTPPortHistoryMaxSyncPathDelay,
    f3PtpL3PTPPortHistoryAvgSyncPathDelay,
    f3PtpL3PTPPortHistoryMinMeanPathDelay,
    f3PtpL3PTPPortHistoryMaxMeanPathDelay,
    f3PtpL3PTPPortHistoryAvgMeanPathDelay,
    f3PtpL3PTPPortHistoryMsgMiscDiscards,

    f3PtpL3PTPPortThresholdIndex, f3PtpL3PTPPortThresholdInterval,
    f3PtpL3PTPPortThresholdVariable, f3PtpL3PTPPortThresholdValueLo,
    f3PtpL3PTPPortThresholdValueHi, f3PtpL3PTPPortThresholdMonValue,

    f3PtpPTPClockStatsIndex,
    f3PtpPTPClockStatsIntervalType,
    f3PtpPTPClockStatsValid,
    f3PtpPTPClockStatsAction,
    f3PtpPTPClockStatsMinOffsetFromMaster,
    f3PtpPTPClockStatsMaxOffsetFromMaster,
    f3PtpPTPClockStatsAvgOffsetFromMaster,
    f3PtpPTPClockStatsMinSyncPathDelay,
    f3PtpPTPClockStatsMaxSyncPathDelay,
    f3PtpPTPClockStatsAvgSyncPathDelay,
    f3PtpPTPClockStatsMinMeanPathDelay,
    f3PtpPTPClockStatsMaxMeanPathDelay,
    f3PtpPTPClockStatsAvgMeanPathDelay,

    f3PtpPTPClockHistoryIndex,
    f3PtpPTPClockHistoryTime,
    f3PtpPTPClockHistoryValid,
    f3PtpPTPClockHistoryAction,
    f3PtpPTPClockHistoryMinOffsetFromMaster,
    f3PtpPTPClockHistoryMaxOffsetFromMaster,
    f3PtpPTPClockHistoryAvgOffsetFromMaster,
    f3PtpPTPClockHistoryMinSyncPathDelay,
    f3PtpPTPClockHistoryMaxSyncPathDelay,
    f3PtpPTPClockHistoryAvgSyncPathDelay,
    f3PtpPTPClockHistoryMinMeanPathDelay,
    f3PtpPTPClockHistoryMaxMeanPathDelay,
    f3PtpPTPClockHistoryAvgMeanPathDelay,

    f3PtpL3RemoteSlaveStatsIndex,
    f3PtpL3RemoteSlaveStatsIntervalType,
    f3PtpL3RemoteSlaveStatsValid,
    f3PtpL3RemoteSlaveStatsAction,
    f3PtpL3RemoteSlaveStatsSyncMsgsGen,
    f3PtpL3RemoteSlaveStatsDelayRspMsgsGen,
    f3PtpL3RemoteSlaveStatsAnnounceMsgsGen,
    f3PtpL3RemoteSlaveStatsSignallingMsgsGen,
    f3PtpL3RemoteSlaveStatsDelayReqMsgsRx,
    f3PtpL3RemoteSlaveStatsSignallingMsgsRx,
    f3PtpL3RemoteSlaveStatsDelayReqMsgsDropped,
    f3PtpL3RemoteSlaveStatsInvalidTLVLenDiscards,
    f3PtpL3RemoteSlaveStatsInvalidTLVTypeDiscards,
    f3PtpL3RemoteSlaveStatsTimesSyncLeaseExp,
    f3PtpL3RemoteSlaveStatsTimesDelayRspLeaseExp,
    f3PtpL3RemoteSlaveStatsTimesAnnounceLeaseExp,

    f3PtpL3RemoteSlaveHistoryIndex,
    f3PtpL3RemoteSlaveHistoryIntervalType,
    f3PtpL3RemoteSlaveHistoryValid,
    f3PtpL3RemoteSlaveHistoryAction,
    f3PtpL3RemoteSlaveHistorySyncMsgsGen,
    f3PtpL3RemoteSlaveHistoryDelayRspMsgsGen,
    f3PtpL3RemoteSlaveHistoryAnnounceMsgsGen,
    f3PtpL3RemoteSlaveHistorySignallingMsgsGen,
    f3PtpL3RemoteSlaveHistoryDelayReqMsgsRx,
    f3PtpL3RemoteSlaveHistorySignallingMsgsRx,
    f3PtpL3RemoteSlaveHistoryDelayReqMsgsDropped,
    f3PtpL3RemoteSlaveHistoryInvalidTLVLenDiscards,
    f3PtpL3RemoteSlaveHistoryInvalidTLVTypeDiscards,
    f3PtpL3RemoteSlaveHistoryTimesSyncLeaseExp,
    f3PtpL3RemoteSlaveHistoryTimesDelayRspLeaseExp,
    f3PtpL3RemoteSlaveHistoryTimesAnnounceLeaseExp,

    f3PtpL3RemoteSlaveThresholdIndex,
    f3PtpL3RemoteSlaveThresholdInterval,
    f3PtpL3RemoteSlaveThresholdVariable,
    f3PtpL3RemoteSlaveThresholdValueLo,
    f3PtpL3RemoteSlaveThresholdValueHi,
    f3PtpL3RemoteSlaveThresholdMonValue,

    f3PtpPTPClockThresholdIndex,
    f3PtpPTPClockThresholdInterval,
    f3PtpPTPClockThresholdVariable,
    f3PtpPTPClockThresholdValueLo,
    f3PtpPTPClockThresholdValueHi,
    f3PtpPTPClockThresholdMonValue,
    

    f3PtpL3PTPPortStatsV2OutOfSequenceAnnouceMessages,
    f3PtpL3PTPPortStatsV2OutOfSequenceSyncMessages,
    f3PtpL3PTPPortStatsV2MgmtMessagesDiscards,
    f3PtpL3PTPPortStatsV2AnnounceDeniedEventsTx,
    f3PtpL3PTPPortStatsV2SyncDeniedEventsTx,
    f3PtpL3PTPPortStatsV2DynamicSlavesLearnedCount,
    f3PtpL3PTPPortStatsV2DynamicSlavesDropped,
    f3PtpL3PTPPortStatsV2DelayRespDeniedEventsTx,
    f3PtpL3PTPPortStatsV2AnnounceCancelledEventsTx,
    f3PtpL3PTPPortStatsV2SyncCancelledEventsTx,
    f3PtpL3PTPPortStatsV2DelayRespCancelledEventsTx,
    f3PtpL3PTPPortStatsV2AnnounceDeniedEventsRx,
    f3PtpL3PTPPortStatsV2SyncDeniedEventsRx,
    f3PtpL3PTPPortStatsV2DelayRespDeniedEventsRx,
    f3PtpL3PTPPortStatsV2AnnounceCancelledEventsRx,
    f3PtpL3PTPPortStatsV2SyncCancelledEventsRx,
    f3PtpL3PTPPortStatsV2DelayRespCancelledEventsRx,
    f3PtpL3PTPPortStatsV2IntervalType,
    f3PtpL3PTPPortStatsV2ValidFlag,
    f3PtpL3PTPPortStatsV2AnnouncesRx,
    f3PtpL3PTPPortStatsV2AnnouncesTx,
    f3PtpL3PTPPortStatsV2SyncsRx,
    f3PtpL3PTPPortStatsV2SyncsTx,
    f3PtpL3PTPPortStatsV2FollowupsRx,
    f3PtpL3PTPPortStatsV2FollowupsTx,
    f3PtpL3PTPPortStatsV2DelayReqsRx,
    f3PtpL3PTPPortStatsV2DelayReqsTx,
    f3PtpL3PTPPortStatsV2DelayRspsRx,
    f3PtpL3PTPPortStatsV2DelayRspsTx,
    f3PtpL3PTPPortStatsV2SignalingRx,
    f3PtpL3PTPPortStatsV2SignalingTx,
    f3PtpL3PTPPortStatsV2MgmtFramesRx,
    f3PtpL3PTPPortStatsV2MgmtFramesTx,
    f3PtpL3PTPPortStatsV2PtpUnknownsRx,
    f3PtpL3PTPPortStatsV2AvgSyncResTime,
    f3PtpL3PTPPortStatsV2MinSyncResTime,
    f3PtpL3PTPPortStatsV2MaxSyncResTime,
    f3PtpL3PTPPortStatsV2AvgDelayReqResTime,
    f3PtpL3PTPPortStatsV2MinDelayReqResTime,
    f3PtpL3PTPPortStatsV2MaxDelayReqResTime,
    f3PtpL3PTPPortStatsV2AvgAnnounceRate,
    f3PtpL3PTPPortStatsV2AvgSyncRate,
    f3PtpL3PTPPortStatsV2AvgDelayReqRate,
    f3PtpL3PTPPortStatsV2AvgDelayRespRate,
    f3PtpL3PTPPortStatsV2MismatchDomainDiscards,
    f3PtpL3PTPPortStatsV2MessageWrongTypeDiscards,
    f3PtpL3PTPPortStatsV2MessagesWrongLengthDiscards,
    f3PtpL3PTPPortStatsV2UnknownMasterDiscards,
    f3PtpL3PTPPortStatsV2MessageMiscDiscards,
    f3PtpL3PTPPortStatsV2Action,
    
    f3PtpL3PTPPortHistoryV2OutOfSequenceAnnouceMessages,
    f3PtpL3PTPPortHistoryV2OutOfSequenceSyncMessages,
    f3PtpL3PTPPortHistoryV2MgmtMessagesDiscards,
    f3PtpL3PTPPortHistoryV2AnnounceDeniedEventsTx,
    f3PtpL3PTPPortHistoryV2SyncDeniedEventsTx,
    f3PtpL3PTPPortHistoryV2DynamicSlavesLearnedCount,
    f3PtpL3PTPPortHistoryV2DynamicSlavesDropped,
    f3PtpL3PTPPortHistoryV2DelayRespDeniedEventsTx,
    f3PtpL3PTPPortHistoryV2AnnounceCancelledEventsTx,
    f3PtpL3PTPPortHistoryV2SyncCancelledEventsTx,
    f3PtpL3PTPPortHistoryV2DelayRespCancelledEventsTx,
    f3PtpL3PTPPortHistoryV2AnnounceDeniedEventsRx,
    f3PtpL3PTPPortHistoryV2SyncDeniedEventsRx,
    f3PtpL3PTPPortHistoryV2DelayRespDeniedEventsRx,
    f3PtpL3PTPPortHistoryV2AnnounceCancelledEventsRx,
    f3PtpL3PTPPortHistoryV2SyncCancelledEventsRx,
    f3PtpL3PTPPortHistoryV2DelayRespCancelledEventsRx,
    f3PtpL3PTPPortHistoryV2IntervalType,
    f3PtpL3PTPPortHistoryV2TimeStamp,
    f3PtpL3PTPPortHistoryV2ValidFlag,
    f3PtpL3PTPPortHistoryV2AnnouncesRx,
    f3PtpL3PTPPortHistoryV2AnnouncesTx,
    f3PtpL3PTPPortHistoryV2SyncsRx,
    f3PtpL3PTPPortHistoryV2SyncsTx,
    f3PtpL3PTPPortHistoryV2FollowupsRx,
    f3PtpL3PTPPortHistoryV2FollowupsTx,
    f3PtpL3PTPPortHistoryV2DelayReqsRx,
    f3PtpL3PTPPortHistoryV2DelayReqsTx,
    f3PtpL3PTPPortHistoryV2DelayRspsRx,
    f3PtpL3PTPPortHistoryV2DelayRspsTx,
    f3PtpL3PTPPortHistoryV2SignalingRx,
    f3PtpL3PTPPortHistoryV2SignalingTx,
    f3PtpL3PTPPortHistoryV2MgmtFramesRx,
    f3PtpL3PTPPortHistoryV2MgmtFramesTx,
    f3PtpL3PTPPortHistoryV2PtpUnknownsRx,
    f3PtpL3PTPPortHistoryV2AvgSyncResTime,
    f3PtpL3PTPPortHistoryV2MinSyncResTime,
    f3PtpL3PTPPortHistoryV2MaxSyncResTime,
    f3PtpL3PTPPortHistoryV2AvgDelayReqResTime,
    f3PtpL3PTPPortHistoryV2MinDelayReqResTime,
    f3PtpL3PTPPortHistoryV2MaxDelayReqResTime,
    f3PtpL3PTPPortHistoryV2AvgAnnounceRate,
    f3PtpL3PTPPortHistoryV2AvgSyncRate,
    f3PtpL3PTPPortHistoryV2AvgDelayReqRate,
    f3PtpL3PTPPortHistoryV2AvgDelayRespRate,
    f3PtpL3PTPPortHistoryV2MismatchDomainDiscards,
    f3PtpL3PTPPortHistoryV2MessageWrongTypeDiscards,
    f3PtpL3PTPPortHistoryV2MessagesWrongLengthDiscards,
    f3PtpL3PTPPortHistoryV2UnknownMasterDiscards,
    f3PtpL3PTPPortHistoryV2MessageMiscDiscards,
    f3PtpL3PTPPortHistoryV2Action
    
    }
    STATUS  current
    DESCRIPTION
        "A collection of objects used to manage the F3 PTP Performance data."
    ::= { f3PtpGroups 2 }

f3PtpPerfNotifGroup NOTIFICATION-GROUP
    NOTIFICATIONS {
        f3PtpAccPortFlowPointThresholdCrossingAlert,
        f3PtpNetPortFlowPointThresholdCrossingAlert,
        f3PtpSOOCCrossingAlert, f3PtpTSCrossingAlert,
        f3PtpPTPClockCrossingAlert,
        f3PtpPTPPortCrossingAlert,
        f3PtpL3PTPPortCrossingAlert
    }
    STATUS  current
    DESCRIPTION
            "A collection of notifications related to F3 PTP Threshold Crossing 
             Alerts."
    ::= { f3PtpGroups 3 }

f3PtpStatusChangeNotifGroup NOTIFICATION-GROUP
    NOTIFICATIONS {
        f3PtpTSStatusChangeTrap 
    }
    STATUS  current
    DESCRIPTION
            "A collection of notifications related to F3 PTP Status Changes ." 
    ::= { f3PtpGroups 4 }

f3PtpBoundaryClockObjectGroup OBJECT-GROUP
    OBJECTS {
       f3PtpBCAlias,
       f3PtpBCAdminState,
       f3PtpBCOperationalState,
       f3PtpBCSecondaryState,
       f3PtpBCClockIdentity,
       f3PtpBCTimingSource,
       f3PtpBCClockClass,
       f3PtpBCDomainNumber,
       f3PtpBCStorageType,
       f3PtpBCRowStatus,
       f3PtpBCMediationControl,
       
       f3PtpMasterClockIndex,
       f3PtpMasterClockAlias,
       f3PtpMasterClockAdminState,
       f3PtpMasterClockOperationalState,
       f3PtpMasterClockSecondaryState,
       f3PtpMasterClockClockIdentity,
       f3PtpMasterClockTimeClock,
       f3PtpMasterClockClockClass,
       f3PtpMasterClockDomainNumber,
       f3PtpMasterClockPriority1,
       f3PtpMasterClockPriority2,
       f3PtpMasterClockClockAccuracy,
       f3PtpMasterClockTimeScale,
       f3PtpMasterClockUtcOffset,
       f3PtpMasterClockStorageType,
       f3PtpMasterClockRowStatus,
       f3PtpMasterClockActiveTimeRef,
       f3PtpMasterClockPTPProfile,
       f3PtpMasterClockServiceAvailableTime, 
       f3PtpMasterClockServiceUnavailableTime, 
       f3PtpMasterClockServiceAvailablePercentage,
       f3PtpMasterClockSmpteSystemFrameRateNumerator,
       f3PtpMasterClockSmpteSystemFrameRateDenominator,
       f3PtpMasterClockSmpteTimeAddressFlags,

       f3PtpMCIAlias,
       f3PtpMCIAdminState,
       f3PtpMCIOperationalState,
       f3PtpMCISecondaryState,
       f3PtpMCIPortIdentity,
       f3PtpMCIDomainNumber,
       f3PtpMCIClockType,
       f3PtpMCIDelayMechanism,
       f3PtpMCIIfName,
       f3PtpMCIIpProtocol,
       f3PtpMCIMasterIpV4Address,
       f3PtpMCIMasterIpV4SubnetMask,
       f3PtpMCIIpPriorityMapMode,
       f3PtpMCIIpPriority,
       f3PtpMCIMaxLeaseDuration,
       f3PtpMCIMaxSlavesSupported,
       f3PtpMCIMaxStaticSlavesSupported,
       f3PtpMCIMaxSyncMsgRate,
       f3PtpMCIMaxDelayRespMsgRate,
       f3PtpMCIMaxAnnounceMsgRate,
       f3PtpMCIStorageType,
       f3PtpMCIRowStatus, 
       f3PtpMCIServiceFlow,
       f3PtpMCIClockClassProfile,
       f3PtpMCIClockClass, 
       f3PtpMCIAnnounceExtTLVEnable,
       f3PtpMCIPtpTransport,
       f3PtpMCIPtpTransportMode,
       f3PtpMCIPtpRemoteSlaveAgingTimeout,
       f3PtpMCIMasterIpV6Address,            
       f3PtpMCIMasterIpV6AddrPrefixLength,
       f3PtpMCIDefaultGatewayControl,
       f3PtpMCIGateway,              
       f3PtpMCIIpV6Gateway,          
       f3PtpMCISlavesWarningThreshold,
       f3PtpMCIForcePRTCClockQuality,


       f3PtpMasterVirtualPortAlias,
       f3PtpMasterVirtualPortAdminState,
       f3PtpMasterVirtualPortOperationalState,
       f3PtpMasterVirtualPortSecondaryState,
       f3PtpMasterVirtualPortFlowPoint,
       f3PtpMasterVirtualPortStorageType,
       f3PtpMasterVirtualPortRowStatus,

       f3PtpStaticRemoteSlaveAlias,
       f3PtpStaticRemoteSlaveAdminState,
       f3PtpStaticRemoteSlaveOperationalState,
       f3PtpStaticRemoteSlaveSecondaryState,
       f3PtpStaticRemoteSlaveClockIdentity,
       f3PtpStaticRemoteSlaveIpV4Address,
       f3PtpStaticRemoteSlaveTimeCreated,
       f3PtpStaticRemoteSlaveSyncMsgRate,
       f3PtpStaticRemoteSlaveDelayRspMsgRate,
       f3PtpStaticRemoteSlaveAnnounceMsgRate,
       f3PtpStaticRemoteSlaveNegSyncLeaseDur,
       f3PtpStaticRemoteSlaveNegDelayRspLeaseDur,
       f3PtpStaticRemoteSlaveNegAnnounceLeaseDur,
       f3PtpStaticRemoteSlaveSyncDurRemTime,
       f3PtpStaticRemoteSlaveDelayRspDurRemTime,
       f3PtpStaticRemoteSlaveAnnounceDurRemTime,
       f3PtpStaticRemoteSlaveUmnControl,
       f3PtpStaticRemoteSlaveStorageType,
       f3PtpStaticRemoteSlaveRowStatus,
       f3PtpStaticRemoteSlaveIpV6Address,

       f3PtpDynamicRemoteSlaveAlias,
       f3PtpDynamicRemoteSlaveAdminState,
       f3PtpDynamicRemoteSlaveOperationalState,
       f3PtpDynamicRemoteSlaveSecondaryState,
       f3PtpDynamicRemoteSlaveClockIdentity,
       f3PtpDynamicRemoteSlaveIpV4Address,
       f3PtpDynamicRemoteSlaveTimeCreated,
       f3PtpDynamicRemoteSlaveSyncMsgRate,
       f3PtpDynamicRemoteSlaveDelayRspMsgRate,
       f3PtpDynamicRemoteSlaveAnnounceMsgRate,
       f3PtpDynamicRemoteSlaveNegSyncLeaseDur,
       f3PtpDynamicRemoteSlaveNegDelayRspLeaseDur,
       f3PtpDynamicRemoteSlaveNegAnnounceLeaseDur,
       f3PtpDynamicRemoteSlaveSyncDurRemTime,
       f3PtpDynamicRemoteSlaveDelayRspDurRemTime,
       f3PtpDynamicRemoteSlaveAnnounceDurRemTime,
       f3PtpDynamicRemoteSlaveRowStatus,
       f3PtpDynamicRemoteSlaveStorageType,
       f3PtpDynamicRemoteSlavePortIdentity,
       f3PtpDynamicRemoteSlavePeerMacAddress,
       f3PtpDynamicRemoteSlaveIpV6Address,

       f3PtpMCIStatsIntervalType,
       f3PtpMCIStatsValid,
       f3PtpMCIStatsAction,
       f3PtpMCIStatsPtpDiscards,
       f3PtpMCIStatsSyncDeniedEvents,
       f3PtpMCIStatsDelayRspDeniedEvents,
       f3PtpMCIStatsAnnounceDeniedEvents,
       f3PtpMCIStatsSyncCancelledEvents,
       f3PtpMCIStatsDelayRspCancelledEvents,
       f3PtpMCIStatsAnnounceCancelledEvents,
       f3PtpMCIStatsDynamicSlavesLearnt,
       f3PtpMCIStatsDynamicSlavesDropped,

       f3PtpMCIHistoryIndex,
       f3PtpTSHistoryTime,
       f3PtpMCIHistoryValid,
       f3PtpMCIHistoryAction,
       f3PtpMCIHistoryPtpDiscards,
       f3PtpMCIHistorySyncDeniedEvents,
       f3PtpMCIHistoryDelayRspDeniedEvents,
       f3PtpMCIHistoryAnnounceDeniedEvents,
       f3PtpMCIHistorySyncCancelledEvents,
       f3PtpMCIHistoryDelayRspCancelledEvents,
       f3PtpMCIHistoryAnnounceCancelledEvents,
       f3PtpMCIHistoryDynamicSlavesLearnt,
       f3PtpMCIHistoryDynamicSlavesDropped,

       f3PtpMCIThresholdInterval,
       f3PtpMCIThresholdVariable,
       f3PtpMCIThresholdValueLo,
       f3PtpMCIThresholdValueHi,
       f3PtpMCIThresholdMonValue,

       f3PtpRemoteSlaveStatsIntervalType,
       f3PtpRemoteSlaveStatsValid,
       f3PtpRemoteSlaveStatsAction,
       f3PtpRemoteSlaveStatsSyncMsgsGen,
       f3PtpRemoteSlaveStatsDelayRspMsgsGen,
       f3PtpRemoteSlaveStatsAnnounceMsgsGen,
       f3PtpRemoteSlaveStatsSignallingMsgsGen,
       f3PtpRemoteSlaveStatsDelayReqMsgsRx,
       f3PtpRemoteSlaveStatsSignallingMsgsRx,
       f3PtpRemoteSlaveStatsDelayReqMsgsDropped,
       f3PtpRemoteSlaveStatsInvalidTLVLenDiscards,
       f3PtpRemoteSlaveStatsInvalidTLVTypeDiscards,
       f3PtpRemoteSlaveStatsTimesSyncLeaseExp,
       f3PtpRemoteSlaveStatsTimesDelayRspLeaseExp,
       f3PtpRemoteSlaveStatsTimesAnnounceLeaseExp,

       f3PtpRemoteSlaveHistoryTime,
       f3PtpRemoteSlaveHistoryValid,
       f3PtpRemoteSlaveHistoryAction,
       f3PtpRemoteSlaveHistorySyncMsgsGen,
       f3PtpRemoteSlaveHistoryDelayRspMsgsGen,
       f3PtpRemoteSlaveHistoryAnnounceMsgsGen,
       f3PtpRemoteSlaveHistorySignallingMsgsGen,
       f3PtpRemoteSlaveHistoryDelayReqMsgsRx,
       f3PtpRemoteSlaveHistorySignallingMsgsRx,
       f3PtpRemoteSlaveHistoryDelayReqMsgsDropped,
       f3PtpRemoteSlaveHistoryInvalidTLVLenDiscards,
       f3PtpRemoteSlaveHistoryInvalidTLVTypeDiscards,
       f3PtpRemoteSlaveHistoryTimesSyncLeaseExp,
       f3PtpRemoteSlaveHistoryTimesDelayRspLeaseExp,
       f3PtpRemoteSlaveHistoryTimesAnnounceLeaseExp,

       f3PtpRemoteSlaveThresholdInterval,
       f3PtpRemoteSlaveThresholdVariable,
       f3PtpRemoteSlaveThresholdValueLo,
       f3PtpRemoteSlaveThresholdValueHi,
       f3PtpRemoteSlaveThresholdMonValue,

       f3PtpL3DynamicRemoteSlaveAlias,
       f3PtpL3DynamicRemoteSlaveAdminState,
       f3PtpL3DynamicRemoteSlaveOperationalState,
       f3PtpL3DynamicRemoteSlaveSecondaryState,
       f3PtpL3DynamicRemoteSlaveClockIdentity,
       f3PtpL3DynamicRemoteSlaveIpV4Address,
       f3PtpL3DynamicRemoteSlaveTimeCreated,
       f3PtpL3DynamicRemoteSlaveSyncMsgRate,
       f3PtpL3DynamicRemoteSlaveDelayRspMsgRate,
       f3PtpL3DynamicRemoteSlaveAnnounceMsgRate,
       f3PtpL3DynamicRemoteSlaveNegSyncLeaseDur,
       f3PtpL3DynamicRemoteSlaveNegDelayRspLeaseDur,
       f3PtpL3DynamicRemoteSlaveNegAnnounceLeaseDur,
       f3PtpL3DynamicRemoteSlaveSyncDurRemTime,
       f3PtpL3DynamicRemoteSlaveDelayRspDurRemTime,
       f3PtpL3DynamicRemoteSlaveAnnounceDurRemTime,
       f3PtpL3DynamicRemoteSlaveIpV6Address,
       f3PtpL3DynamicRemoteSlaveRowStatus,
       f3PtpL3DynamicRemoteSlaveStorageType
    }
    STATUS  current
    DESCRIPTION
            "A collection of objects related to F3 PTP Boundary Clock feature." 
    ::= { f3PtpGroups 5 }

f3PtpBoundaryClockNotifGroup NOTIFICATION-GROUP
    NOTIFICATIONS {
       f3PtpMCICrossingAlert,
       f3PtpRemoteSlaveCrossingAlert,
       f3PtpMasterClockStatusChangeTrap,     
       f3PtpBCStatusChangeTrap,  
       f3PtpDynamicRemoteSlaveStatusChangeTrap,
       f3PtpL3DynamicRemoteSlaveStatusChangeTrap,
       f3PtpL3RemoteSlaveCrossingAlert
    }
    STATUS  current
    DESCRIPTION
            "A collection of notifications related to F3 PTP Boundary Clock feature." 
    ::= { f3PtpGroups 6 }

f3PtpProtObjectGroup OBJECT-GROUP
    OBJECTS {
        f3PtpMCIProtGroupIndex, f3PtpMCIProtGroupAdminState,
        f3PtpMCIProtGroupActiveMember,
        f3PtpMCIProtGroupLastSwitchOverTime, f3PtpMCIProtGroupLastSwitchOverReason,
        f3PtpMCIProtGroupStorageType, f3PtpMCIProtGroupRowStatus, f3PtpMCIProtGroupPriority,
        
        f3PtpMCIProtMemberObject, f3PtpMCIProtMemberStorageType, f3PtpMCIProtMemberRowStatus
    }
    STATUS  current
    DESCRIPTION
        "A collection of objects used to manage the Protection Object group."
    ::= { f3PtpGroups 7 }

END
